# =============================================================================
#  TrackAssembly.FCMacro  v1
#  –  Complete track assembly: chain + drive wheels in one shot
# =============================================================================
#
#  WORKFLOW
#  --------
#  1. Select the track-link body in the 3-D view, then run the macro.
#  2. A dialog opens — the 3-D view stays fully interactive.
#  3. Click the LEFT hole edge, then [Pick Left Joint].
#     Click the RIGHT hole edge, then [Pick Right Joint].
#  4. Set wheel diameter D, width W, hub bore, and link body height H.
#  5. The Computed panel shows N_per_arc, total links, arc radius, etc.
#  6. Set links per straight side and loop direction.
#  7. Choose which objects to generate (chain, left wheel, right wheel).
#  8. Click [Generate Assembly].
#
#  OUTPUT
#  ------
#  • TrackChain_<N>links_<up|down>  — chain compound (N copies of the link)
#  • Wheel_Left_D<D>mm              — left wheel cylinder  (optional)
#  • Wheel_Right_D<D>mm             — right wheel cylinder (optional)
#
#  GEOMETRY
#  --------
#  Wheel diameter D drives N_per_arc = round(π / (2·arcsin(pitch/D))).
#  Arc radius    R = pitch / (2·sin(π / (2·N_per_arc)))   (chord-based)
#  Total links   N = 2·N_per_arc + 2·N_straight
#  Wheel centers at (±half_straight, 0) in world space — exactly at the
#  arc centers so the chain rides flush on the wheel rims.
#
#  MINIMUM WHEEL DIAMETER
#  ----------------------
#  R_min = pitch² / H  +  H / 4     (link body must clear the rim)
#  D_min = 2 × R_min
#
# =============================================================================

import FreeCAD
import FreeCADGui
import Part
import math

try:
    from PySide6 import QtWidgets, QtCore, QtGui
except ImportError:
    try:
        from PySide2 import QtWidgets, QtCore, QtGui
    except ImportError:
        from PySide import QtWidgets, QtCore, QtGui

# Qt5/Qt6 enum compat shims
try:
    _Qt_NoPen       = QtCore.Qt.PenStyle.NoPen
    _Qt_DashLine    = QtCore.Qt.PenStyle.DashLine
    _Qt_AlignCenter = QtCore.Qt.AlignmentFlag.AlignCenter
    _Qt_AlignLeft   = QtCore.Qt.AlignmentFlag.AlignLeft
    _Qt_Antialias   = QtGui.QPainter.RenderHint.Antialiasing
except AttributeError:
    _Qt_NoPen       = getattr(QtCore.Qt, 'NoPen')
    _Qt_DashLine    = getattr(QtCore.Qt, 'DashLine')
    _Qt_AlignCenter = getattr(QtCore.Qt, 'AlignCenter')
    _Qt_AlignLeft   = getattr(QtCore.Qt, 'AlignLeft')
    _Qt_Antialias   = getattr(QtGui.QPainter, 'Antialiasing')


# ── QtSvg import ─────────────────────────────────────────────────────────────

try:
    from PySide6 import QtSvg as _QtSvg
except ImportError:
    try:
        from PySide2 import QtSvg as _QtSvg
    except ImportError:
        _QtSvg = None


# ── embedded SVG diagrams ─────────────────────────────────────────────────────

_SVG_LINK  = 'link'
_SVG_WHEEL = 'wheel'
_SVG_H     = 'h'
_SVG_DIST  = 'dist'
_SVG_SYM   = 'sym'

_SVG_DATA_LINK = b"""<svg xmlns="http://www.w3.org/2000/svg" viewBox="0 0 300 88" font-family="system-ui,sans-serif">
  <rect width="300" height="88" fill="#f8fafd"/>
  <rect x="28" y="22" width="244" height="32" rx="12" ry="12" fill="#90bbd8" stroke="#1e5d8c" stroke-width="2"/>
  <circle cx="54"  cy="38" r="11" fill="#1e5d8c"/>
  <circle cx="54"  cy="38" r="4"  fill="#f8fafd"/>
  <circle cx="246" cy="38" r="11" fill="#1e5d8c"/>
  <circle cx="246" cy="38" r="4"  fill="#f8fafd"/>
  <text x="54"  y="13" text-anchor="middle" font-size="8" fill="#32404e">Left Joint</text>
  <text x="246" y="13" text-anchor="middle" font-size="8" fill="#32404e">Right Joint</text>
  <line x1="54"  y1="57" x2="54"  y2="69" stroke="#c62828" stroke-width="1.5"/>
  <line x1="246" y1="57" x2="246" y2="69" stroke="#c62828" stroke-width="1.5"/>
  <line x1="54"  y1="65" x2="246" y2="65" stroke="#c62828" stroke-width="1.5"/>
  <polygon points="54,65 63,61 63,69"   fill="#c62828"/>
  <polygon points="246,65 237,61 237,69" fill="#c62828"/>
  <text x="150" y="80" text-anchor="middle" font-size="8" font-style="italic" fill="#c62828">pitch</text>
</svg>"""

_SVG_DATA_WHEEL = b"""<svg xmlns="http://www.w3.org/2000/svg" viewBox="0 0 300 132" font-family="system-ui,sans-serif">
  <rect width="300" height="132" fill="#f8fafd"/>
  <text x="74"  y="11" text-anchor="middle" font-size="8" font-style="italic" fill="#969696">front view</text>
  <circle cx="74" cy="74" r="50" fill="#90bbd8" stroke="#1e5d8c" stroke-width="2"/>
  <circle cx="74" cy="74" r="13" fill="#f8fafd" stroke="#1e5d8c" stroke-width="1.5"/>
  <line x1="87" y1="70" x2="105" y2="55" stroke="#969696" stroke-width="1"/>
  <text x="107" y="59" font-size="8" fill="#969696">hub &#x2300;</text>
  <line x1="127" y1="24"  x2="140" y2="24"  stroke="#c62828" stroke-width="1.2"/>
  <line x1="127" y1="124" x2="140" y2="124" stroke="#c62828" stroke-width="1.2"/>
  <line x1="137" y1="24"  x2="137" y2="124" stroke="#c62828" stroke-width="1.5"/>
  <polygon points="137,24  133,34 141,34"   fill="#c62828"/>
  <polygon points="137,124 133,114 141,114" fill="#c62828"/>
  <text x="148" y="79" text-anchor="middle" font-size="11" font-weight="bold" fill="#c62828">D</text>
  <text x="228" y="11" text-anchor="middle" font-size="8" font-style="italic" fill="#969696">side view</text>
  <rect x="202" y="24" width="52" height="100" fill="#90bbd8" stroke="#1e5d8c" stroke-width="2"/>
  <rect x="202" y="61" width="52" height="26"  fill="#f8fafd" stroke="#1e5d8c" stroke-width="1" stroke-dasharray="4,3"/>
  <line x1="202" y1="14" x2="254" y2="14" stroke="#c62828" stroke-width="1.5"/>
  <line x1="202" y1="10" x2="202" y2="20" stroke="#c62828" stroke-width="1.5"/>
  <line x1="254" y1="10" x2="254" y2="20" stroke="#c62828" stroke-width="1.5"/>
  <polygon points="202,14 211,10 211,18" fill="#c62828"/>
  <polygon points="254,14 245,10 245,18" fill="#c62828"/>
  <text x="228" y="10" text-anchor="middle" font-size="10" font-weight="bold" fill="#c62828">W</text>
  <line x1="259" y1="24"  x2="272" y2="24"  stroke="#c62828" stroke-width="1.2"/>
  <line x1="259" y1="124" x2="272" y2="124" stroke="#c62828" stroke-width="1.2"/>
  <line x1="269" y1="24"  x2="269" y2="124" stroke="#c62828" stroke-width="1.5"/>
  <polygon points="269,24  265,34 273,34"   fill="#c62828"/>
  <polygon points="269,124 265,114 273,114" fill="#c62828"/>
  <text x="281" y="79" text-anchor="middle" font-size="11" font-weight="bold" fill="#c62828">D</text>
</svg>"""

_SVG_DATA_H = b"""<svg xmlns="http://www.w3.org/2000/svg" viewBox="0 0 280 90" font-family="system-ui,sans-serif">
  <rect width="280" height="90" fill="#f8fafd"/>
  <rect x="26" y="25" width="210" height="40" rx="10" ry="10" fill="#90bbd8" stroke="#1e5d8c" stroke-width="1.5"/>
  <circle cx="52"  cy="45" r="10" fill="#1e5d8c"/>
  <circle cx="52"  cy="45" r="4"  fill="#f8fafd"/>
  <circle cx="210" cy="45" r="10" fill="#1e5d8c"/>
  <circle cx="210" cy="45" r="4"  fill="#f8fafd"/>
  <line x1="245" y1="25" x2="257" y2="25" stroke="#c62828" stroke-width="1.2"/>
  <line x1="245" y1="65" x2="257" y2="65" stroke="#c62828" stroke-width="1.2"/>
  <line x1="251" y1="27" x2="251" y2="63" stroke="#c62828" stroke-width="1.5"/>
  <polygon points="251,25 247,36 255,36" fill="#c62828"/>
  <polygon points="251,65 247,54 255,54" fill="#c62828"/>
  <text x="264" y="51" text-anchor="middle" font-size="13" font-weight="bold" fill="#c62828">H</text>
</svg>"""

_SVG_DATA_DIST = b"""<svg xmlns="http://www.w3.org/2000/svg" viewBox="0 0 300 90" font-family="system-ui,sans-serif">
  <rect width="300" height="90" fill="#f8fafd"/>
  <circle cx="55"  cy="42" r="28" fill="#90bbd8" stroke="#1e5d8c" stroke-width="1.5"/>
  <circle cx="55"  cy="42" r="7"  fill="#f8fafd" stroke="#1e5d8c" stroke-width="1"/>
  <circle cx="245" cy="42" r="28" fill="#90bbd8" stroke="#1e5d8c" stroke-width="1.5"/>
  <circle cx="245" cy="42" r="7"  fill="#f8fafd" stroke="#1e5d8c" stroke-width="1"/>
  <line x1="55"  y1="14" x2="245" y2="14" stroke="#1e5d8c" stroke-width="2" stroke-dasharray="6,4"/>
  <line x1="55"  y1="70" x2="245" y2="70" stroke="#1e5d8c" stroke-width="2" stroke-dasharray="6,4"/>
  <line x1="55"  y1="82" x2="245" y2="82" stroke="#c62828" stroke-width="1.5"/>
  <line x1="55"  y1="77" x2="55"  y2="87" stroke="#c62828" stroke-width="1.5"/>
  <line x1="245" y1="77" x2="245" y2="87" stroke="#c62828" stroke-width="1.5"/>
  <polygon points="55,82  65,78  65,86"  fill="#c62828"/>
  <polygon points="245,82 235,78 235,86" fill="#c62828"/>
  <text x="150" y="79" text-anchor="middle" font-size="9" font-style="italic" fill="#c62828">distance</text>
</svg>"""

_SVG_DATA_SYM = b"""<svg xmlns="http://www.w3.org/2000/svg" viewBox="0 0 300 110" font-family="system-ui,sans-serif">
  <rect width="300" height="110" fill="#f8fafd"/>
  <text x="72"  y="11" text-anchor="middle" font-size="8" font-style="italic" fill="#969696">symmetric</text>
  <text x="228" y="11" text-anchor="middle" font-size="8" font-style="italic" fill="#969696">one-sided</text>
  <rect x="32"  y="20" width="80" height="60" fill="#90bbd8" stroke="#1e5d8c" stroke-width="1.5"/>
  <rect x="188" y="20" width="80" height="60" fill="#90bbd8" stroke="#1e5d8c" stroke-width="1.5"/>
  <line x1="72"  y1="14" x2="72"  y2="92" stroke="#c62828" stroke-width="1.5" stroke-dasharray="5,3"/>
  <text x="72"  y="12" text-anchor="middle" font-size="7" fill="#c62828">Z=0</text>
  <line x1="188" y1="14" x2="188" y2="92" stroke="#c62828" stroke-width="1.5" stroke-dasharray="5,3"/>
  <text x="188" y="12" text-anchor="middle" font-size="7" fill="#c62828">Z=0</text>
  <line x1="32"  y1="88" x2="112" y2="88" stroke="#c62828" stroke-width="1.2"/>
  <line x1="32"  y1="84" x2="32"  y2="92" stroke="#c62828" stroke-width="1.2"/>
  <line x1="72"  y1="84" x2="72"  y2="92" stroke="#c62828" stroke-width="1.2"/>
  <line x1="112" y1="84" x2="112" y2="92" stroke="#c62828" stroke-width="1.2"/>
  <polygon points="32,88  41,84  41,92"  fill="#c62828"/>
  <polygon points="72,88  63,84  63,92"  fill="#c62828"/>
  <polygon points="72,88  81,84  81,92"  fill="#c62828"/>
  <polygon points="112,88 103,84 103,92" fill="#c62828"/>
  <text x="52"  y="103" text-anchor="middle" font-size="8" fill="#c62828">W/2</text>
  <text x="92"  y="103" text-anchor="middle" font-size="8" fill="#c62828">W/2</text>
  <line x1="188" y1="88" x2="268" y2="88" stroke="#c62828" stroke-width="1.2"/>
  <line x1="188" y1="84" x2="188" y2="92" stroke="#c62828" stroke-width="1.2"/>
  <line x1="268" y1="84" x2="268" y2="92" stroke="#c62828" stroke-width="1.2"/>
  <polygon points="188,88 197,84 197,92" fill="#c62828"/>
  <polygon points="268,88 259,84 259,92" fill="#c62828"/>
  <text x="228" y="103" text-anchor="middle" font-size="8" fill="#c62828">W</text>
</svg>"""

_SVG_DIR  = 'dir'

_SVG_DATA_DIR = b"""<svg xmlns="http://www.w3.org/2000/svg" viewBox="0 0 300 92" font-family="system-ui,sans-serif">
  <rect width="300" height="92" fill="#f8fafd"/>
  <line x1="150" y1="5" x2="150" y2="88" stroke="#dde3ea" stroke-width="1"/>

  <!-- UP: oval above the line -->
  <text x="75" y="12" text-anchor="middle" font-size="11" font-weight="bold" fill="#43a047">UP</text>
  <rect x="12" y="16" width="126" height="52" rx="26" ry="26"
        fill="none" stroke="#1e5d8c" stroke-width="2.5"/>
  <line x1="45" y1="78" x2="105" y2="78" stroke="#1e5d8c" stroke-width="2.5" stroke-linecap="round"/>

  <!-- DOWN: oval below the line -->
  <text x="225" y="12" text-anchor="middle" font-size="11" font-weight="bold" fill="#c62828">DOWN</text>
  <line x1="195" y1="22" x2="255" y2="22" stroke="#1e5d8c" stroke-width="2.5" stroke-linecap="round"/>
  <rect x="162" y="32" width="126" height="52" rx="26" ry="26"
        fill="none" stroke="#1e5d8c" stroke-width="2.5"/>
</svg>"""

_DIAG_SVG = {
    'link': _SVG_DATA_LINK, 'wheel': _SVG_DATA_WHEEL,
    'h':    _SVG_DATA_H,    'dist':  _SVG_DATA_DIST,
    'sym':  _SVG_DATA_SYM,  'dir':   _SVG_DATA_DIR,
}
_DIAG_CACHE = {}


def _render_svg(svg_bytes, lw, lh):
    pm = QtGui.QPixmap(lw, lh)
    pm.fill(QtGui.QColor(248, 250, 252))
    renderer = _QtSvg.QSvgRenderer(QtCore.QByteArray(svg_bytes))
    p = QtGui.QPainter(pm)
    renderer.render(p, QtCore.QRectF(0, 0, lw, lh))
    p.end()
    return pm


# ── QPainter fallback diagrams (used when QtSvg is not available) ─────────────

def _pm2(W, H):
    pm = QtGui.QPixmap(W, H)
    pm.fill(QtGui.QColor(248, 250, 252))
    p = QtGui.QPainter(pm)
    p.setRenderHint(_Qt_Antialias)
    return pm, p, lambda v: v

def _f(px, bold=False, italic=False):
    f = QtGui.QFont(); f.setPixelSize(px); f.setBold(bold); f.setItalic(italic); return f

def _tri(p, pts, c):
    p.setPen(_Qt_NoPen); p.setBrush(QtGui.QBrush(c))
    p.drawPolygon(QtGui.QPolygon([QtCore.QPoint(*pt) for pt in pts]))

def _mk_link_pm():
    pm, p, s = _pm2(300, 88)
    CB = QtGui.QColor(144,187,216); CP = QtGui.QColor(30,93,140)
    CW = QtGui.QColor(248,250,252); CR = QtGui.QColor(198,40,40)
    p.setPen(QtGui.QPen(CP, s(2))); p.setBrush(QtGui.QBrush(CB))
    p.drawRoundedRect(s(28),s(22),s(244),s(32),s(12),s(12))
    for cx,cy in ((54,38),(246,38)):
        p.setPen(_Qt_NoPen); p.setBrush(QtGui.QBrush(CP))
        p.drawEllipse(s(cx)-s(11),s(cy)-s(11),s(22),s(22))
        p.setBrush(QtGui.QBrush(CW))
        p.drawEllipse(s(cx)-s(4),s(cy)-s(4),s(8),s(8))
    p.setPen(QtGui.QPen(QtGui.QColor(50,64,78))); p.setFont(_f(s(8)))
    p.drawText(QtCore.QRect(s(24),s(4),s(60),s(13)),_Qt_AlignCenter,"Left Joint")
    p.drawText(QtCore.QRect(s(216),s(4),s(60),s(13)),_Qt_AlignCenter,"Right Joint")
    p.setPen(QtGui.QPen(CR, s(1.5)))
    for x in (54,246): p.drawLine(s(x),s(57),s(x),s(69))
    p.drawLine(s(54),s(65),s(246),s(65))
    _tri(p,((s(54),s(65)),(s(63),s(61)),(s(63),s(69))),CR)
    _tri(p,((s(246),s(65)),(s(237),s(61)),(s(237),s(69))),CR)
    p.setPen(QtGui.QPen(CR)); p.setFont(_f(s(8),italic=True))
    p.drawText(QtCore.QRect(s(100),s(72),s(100),s(13)),_Qt_AlignCenter,"pitch")
    p.end(); return pm

def _mk_wheel_pm():
    pm, p, s = _pm2(300, 132)
    CB = QtGui.QColor(144,187,216); CP = QtGui.QColor(30,93,140)
    CW = QtGui.QColor(248,250,252); CR = QtGui.QColor(198,40,40)
    CG = QtGui.QColor(150,150,150)
    p.setPen(QtGui.QPen(CG)); p.setFont(_f(s(8),italic=True))
    p.drawText(QtCore.QRect(s(44),s(2),s(60),s(11)),_Qt_AlignCenter,"front view")
    p.setPen(QtGui.QPen(CP, s(2))); p.setBrush(QtGui.QBrush(CB))
    p.drawEllipse(s(74)-s(50),s(74)-s(50),s(100),s(100))
    p.setPen(QtGui.QPen(CP, s(1.5))); p.setBrush(QtGui.QBrush(CW))
    p.drawEllipse(s(74)-s(13),s(74)-s(13),s(26),s(26))
    p.setPen(QtGui.QPen(CG, s(1))); p.drawLine(s(87),s(70),s(105),s(55))
    p.setPen(QtGui.QPen(CG)); p.setFont(_f(s(8)))
    p.drawText(QtCore.QRect(s(104),s(48),s(35),s(11)),_Qt_AlignLeft,"hub ⌀")
    p.setPen(QtGui.QPen(CR, s(1.2)))
    p.drawLine(s(127),s(24),s(140),s(24)); p.drawLine(s(127),s(124),s(140),s(124))
    p.setPen(QtGui.QPen(CR, s(1.5))); p.drawLine(s(137),s(24),s(137),s(124))
    _tri(p,((s(137),s(24)),(s(133),s(34)),(s(141),s(34))),CR)
    _tri(p,((s(137),s(124)),(s(133),s(114)),(s(141),s(114))),CR)
    p.setPen(QtGui.QPen(CR)); p.setFont(_f(s(11),bold=True))
    p.drawText(QtCore.QRect(s(141),s(68),s(14),s(18)),_Qt_AlignCenter,"D")
    p.setPen(QtGui.QPen(CG)); p.setFont(_f(s(8),italic=True))
    p.drawText(QtCore.QRect(s(198),s(2),s(60),s(11)),_Qt_AlignCenter,"side view")
    p.setPen(QtGui.QPen(CP, s(2))); p.setBrush(QtGui.QBrush(CB))
    p.drawRect(s(202),s(24),s(52),s(100))
    dp = QtGui.QPen(CP, s(1)); dp.setStyle(_Qt_DashLine)
    p.setPen(dp); p.setBrush(QtGui.QBrush(CW)); p.drawRect(s(202),s(61),s(52),s(26))
    p.setPen(QtGui.QPen(CR, s(1.5)))
    p.drawLine(s(202),s(14),s(254),s(14))
    p.drawLine(s(202),s(10),s(202),s(20)); p.drawLine(s(254),s(10),s(254),s(20))
    _tri(p,((s(202),s(14)),(s(211),s(10)),(s(211),s(18))),CR)
    _tri(p,((s(254),s(14)),(s(245),s(10)),(s(245),s(18))),CR)
    p.setPen(QtGui.QPen(CR)); p.setFont(_f(s(10),bold=True))
    p.drawText(QtCore.QRect(s(218),s(6),s(20),s(12)),_Qt_AlignCenter,"W")
    p.setPen(QtGui.QPen(CR, s(1.2)))
    p.drawLine(s(259),s(24),s(272),s(24)); p.drawLine(s(259),s(124),s(272),s(124))
    p.setPen(QtGui.QPen(CR, s(1.5))); p.drawLine(s(269),s(24),s(269),s(124))
    _tri(p,((s(269),s(24)),(s(265),s(34)),(s(273),s(34))),CR)
    _tri(p,((s(269),s(124)),(s(265),s(114)),(s(273),s(114))),CR)
    p.setPen(QtGui.QPen(CR)); p.setFont(_f(s(11),bold=True))
    p.drawText(QtCore.QRect(s(274),s(68),s(14),s(18)),_Qt_AlignCenter,"D")
    p.end(); return pm

def _mk_h_pm():
    pm, p, s = _pm2(280, 90)
    CB = QtGui.QColor(144,187,216); CP = QtGui.QColor(30,93,140)
    CW = QtGui.QColor(248,250,252); CR = QtGui.QColor(198,40,40)
    p.setPen(QtGui.QPen(CP, s(1.5))); p.setBrush(QtGui.QBrush(CB))
    p.drawRoundedRect(s(26),s(25),s(210),s(40),s(10),s(10))
    for cx,cy in ((52,45),(210,45)):
        p.setPen(_Qt_NoPen); p.setBrush(QtGui.QBrush(CP))
        p.drawEllipse(s(cx)-s(10),s(cy)-s(10),s(20),s(20))
        p.setBrush(QtGui.QBrush(CW)); p.drawEllipse(s(cx)-s(4),s(cy)-s(4),s(8),s(8))
    p.setPen(QtGui.QPen(CR, s(1.2)))
    p.drawLine(s(245),s(25),s(257),s(25)); p.drawLine(s(245),s(65),s(257),s(65))
    p.setPen(QtGui.QPen(CR, s(1.5))); p.drawLine(s(251),s(27),s(251),s(63))
    _tri(p,((s(251),s(25)),(s(247),s(36)),(s(255),s(36))),CR)
    _tri(p,((s(251),s(65)),(s(247),s(54)),(s(255),s(54))),CR)
    p.setPen(QtGui.QPen(CR)); p.setFont(_f(s(13),bold=True))
    p.drawText(QtCore.QRect(s(260),s(39),s(16),s(18)),_Qt_AlignCenter,"H")
    p.end(); return pm

def _mk_dist_pm():
    pm, p, s = _pm2(300, 90)
    CB = QtGui.QColor(144,187,216); CP = QtGui.QColor(30,93,140)
    CW = QtGui.QColor(248,250,252); CR = QtGui.QColor(198,40,40)
    for cx,cy,ro,ri in ((55,42,28,7),(245,42,28,7)):
        p.setPen(QtGui.QPen(CP, s(1.5))); p.setBrush(QtGui.QBrush(CB))
        p.drawEllipse(s(cx)-s(ro),s(cy)-s(ro),s(ro*2),s(ro*2))
        p.setPen(QtGui.QPen(CP, s(1))); p.setBrush(QtGui.QBrush(CW))
        p.drawEllipse(s(cx)-s(ri),s(cy)-s(ri),s(ri*2),s(ri*2))
    dp = QtGui.QPen(CP, s(2)); dp.setStyle(_Qt_DashLine); p.setPen(dp)
    p.drawLine(s(55),s(14),s(245),s(14)); p.drawLine(s(55),s(70),s(245),s(70))
    p.setPen(QtGui.QPen(CR, s(1.5)))
    p.drawLine(s(55),s(82),s(245),s(82))
    p.drawLine(s(55),s(77),s(55),s(87)); p.drawLine(s(245),s(77),s(245),s(87))
    _tri(p,((s(55),s(82)),(s(65),s(78)),(s(65),s(86))),CR)
    _tri(p,((s(245),s(82)),(s(235),s(78)),(s(235),s(86))),CR)
    p.setPen(QtGui.QPen(CR)); p.setFont(_f(s(9),italic=True))
    p.drawText(QtCore.QRect(s(100),s(73),s(100),s(12)),_Qt_AlignCenter,"distance")
    p.end(); return pm

def _mk_sym_pm():
    pm, p, s = _pm2(300, 110)
    CB = QtGui.QColor(144,187,216); CP = QtGui.QColor(30,93,140)
    CR = QtGui.QColor(198,40,40);   CG = QtGui.QColor(150,150,150)
    p.setPen(QtGui.QPen(CG)); p.setFont(_f(s(8),italic=True))
    p.drawText(QtCore.QRect(s(32),s(2),s(80),s(11)),_Qt_AlignCenter,"symmetric")
    p.drawText(QtCore.QRect(s(188),s(2),s(80),s(11)),_Qt_AlignCenter,"one-sided")
    for x0 in (32, 188):
        p.setPen(QtGui.QPen(CP, s(1.5))); p.setBrush(QtGui.QBrush(CB))
        p.drawRect(s(x0),s(20),s(80),s(60))
    for xz,label in ((72,"Z=0"),(188,"Z=0")):
        dp = QtGui.QPen(CR, s(1.5)); dp.setStyle(_Qt_DashLine); p.setPen(dp)
        p.drawLine(s(xz),s(14),s(xz),s(92))
        p.setPen(QtGui.QPen(CR)); p.setFont(_f(s(7)))
        p.drawText(QtCore.QRect(s(xz)-s(7),s(7),s(14),s(9)),_Qt_AlignCenter,label)
    p.setPen(QtGui.QPen(CR, s(1.2)))
    p.drawLine(s(32),s(88),s(112),s(88))
    for xt in (32,72,112): p.drawLine(s(xt),s(84),s(xt),s(92))
    _tri(p,((s(32),s(88)),(s(41),s(84)),(s(41),s(92))),CR)
    _tri(p,((s(72),s(88)),(s(63),s(84)),(s(63),s(92))),CR)
    _tri(p,((s(72),s(88)),(s(81),s(84)),(s(81),s(92))),CR)
    _tri(p,((s(112),s(88)),(s(103),s(84)),(s(103),s(92))),CR)
    p.setPen(QtGui.QPen(CR)); p.setFont(_f(s(8)))
    p.drawText(QtCore.QRect(s(35),s(93),s(32),s(12)),_Qt_AlignCenter,"W/2")
    p.drawText(QtCore.QRect(s(75),s(93),s(32),s(12)),_Qt_AlignCenter,"W/2")
    p.setPen(QtGui.QPen(CR, s(1.2)))
    p.drawLine(s(188),s(88),s(268),s(88))
    p.drawLine(s(188),s(84),s(188),s(92)); p.drawLine(s(268),s(84),s(268),s(92))
    _tri(p,((s(188),s(88)),(s(197),s(84)),(s(197),s(92))),CR)
    _tri(p,((s(268),s(88)),(s(259),s(84)),(s(259),s(92))),CR)
    p.setPen(QtGui.QPen(CR)); p.setFont(_f(s(8)))
    p.drawText(QtCore.QRect(s(215),s(93),s(22),s(12)),_Qt_AlignCenter,"W")
    p.end(); return pm

def _mk_dir_pm():
    pm, p, s = _pm2(300, 92)
    CB   = QtGui.QColor(30, 93, 140)
    CUp  = QtGui.QColor(67, 160, 71)
    CDn  = QtGui.QColor(198, 40, 40)
    CSep = QtGui.QColor(220, 227, 234)
    p.setPen(QtGui.QPen(CSep, s(1)))
    p.drawLine(s(150), s(5), s(150), s(88))
    pen = QtGui.QPen(CB, s(2)); pen.setCapStyle(QtCore.Qt.RoundCap)
    # UP: oval above, line below
    p.setPen(QtGui.QPen(CUp)); p.setFont(_f(s(11), bold=True))
    p.drawText(QtCore.QRect(s(0),s(2),s(150),s(14)),_Qt_AlignCenter,"UP")
    p.setPen(pen); p.setBrush(QtGui.QBrush())
    p.drawRoundedRect(QtCore.QRect(s(12),s(16),s(126),s(52)), s(26), s(26))
    p.drawLine(s(45),s(78),s(105),s(78))
    # DOWN: line above, oval below
    p.setPen(QtGui.QPen(CDn)); p.setFont(_f(s(11), bold=True))
    p.drawText(QtCore.QRect(s(150),s(2),s(150),s(14)),_Qt_AlignCenter,"DOWN")
    p.setPen(pen); p.setBrush(QtGui.QBrush())
    p.drawLine(s(195),s(22),s(255),s(22))
    p.drawRoundedRect(QtCore.QRect(s(162),s(32),s(126),s(52)), s(26), s(26))
    p.end(); return pm

_DIAG_PAINTER = {
    'link': _mk_link_pm, 'wheel': _mk_wheel_pm,
    'h':    _mk_h_pm,    'dist':  _mk_dist_pm,
    'sym':  _mk_sym_pm,  'dir':   _mk_dir_pm,
}


def _get_pm(key):
    if key not in _DIAG_CACHE:
        if _QtSvg and key in _DIAG_SVG:
            svg = _DIAG_SVG[key]
            r   = _QtSvg.QSvgRenderer(QtCore.QByteArray(svg))
            sz  = r.defaultSize()
            _DIAG_CACHE[key] = _render_svg(svg, sz.width(), sz.height())
        elif key in _DIAG_PAINTER:
            _DIAG_CACHE[key] = _DIAG_PAINTER[key]()
        else:
            _DIAG_CACHE[key] = None
    return _DIAG_CACHE[key]


# ── hover-popup tooltip ───────────────────────────────────────────────────────

class _SvgTip(QtWidgets.QFrame):
    """Singleton borderless popup rendering a crisp SVG next to a hovered widget."""
    _inst = None

    @classmethod
    def get(cls):
        if cls._inst is None:
            cls._inst = cls(FreeCADGui.getMainWindow())
        return cls._inst

    def __init__(self, parent):
        super().__init__(
            parent,
            QtCore.Qt.ToolTip | QtCore.Qt.FramelessWindowHint |
            QtCore.Qt.NoDropShadowWindowHint
        )
        self.setAttribute(QtCore.Qt.WA_ShowWithoutActivating)
        self.setStyleSheet(
            "QFrame { background:#fffef5; border:1px solid #c8a44a; border-radius:6px; }"
        )
        self._img = QtWidgets.QLabel()
        self._img.setAlignment(_Qt_AlignCenter)
        self._cap = QtWidgets.QLabel()
        self._cap.setAlignment(_Qt_AlignCenter)
        self._cap.setStyleSheet(
            "color:#333; font-size:11px; padding:0 6px 4px; border:none;"
        )
        self._cap.setWordWrap(True)
        lay = QtWidgets.QVBoxLayout(self)
        lay.setContentsMargins(6, 6, 6, 4)
        lay.setSpacing(3)
        lay.addWidget(self._img)
        lay.addWidget(self._cap)
        self.hide()

    def show_svg(self, widget, pixmap, caption):
        self._img.setPixmap(pixmap)
        self._img.setFixedSize(pixmap.width(), pixmap.height())
        if caption:
            self._cap.setText(caption)
            self._cap.setMaximumWidth(pixmap.width())
            self._cap.show()
        else:
            self._cap.hide()
        self.adjustSize()
        gp  = widget.mapToGlobal(QtCore.QPoint(widget.width() + 10, 0))
        try:
            scr = widget.screen().availableGeometry()
        except Exception:
            scr = QtWidgets.QApplication.primaryScreen().availableGeometry()
        if gp.x() + self.width() > scr.right():
            gp = widget.mapToGlobal(QtCore.QPoint(0, widget.height() + 6))
        self.move(gp)
        self.show()
        self.raise_()

    def eventFilter(self, obj, event):
        t = event.type()
        if t == QtCore.QEvent.Enter:
            pm  = obj.property("_svgtip_pm")
            cap = obj.property("_svgtip_cap") or ""
            if pm:
                self.show_svg(obj, pm, cap)
        elif t in (QtCore.QEvent.Leave, QtCore.QEvent.Hide,
                   QtCore.QEvent.WindowDeactivate):
            self.hide()
        elif t == QtCore.QEvent.ToolTip:
            if obj.property("_svgtip_pm"):
                return True          # suppress Qt's text tooltip
        return False


def _attach_svg_tip(widget, key, w=0, h=0, caption="", tip_width=280):
    """Attach a diagram popup to widget on hover."""
    if _QtSvg and key in _DIAG_SVG:
        svg      = _DIAG_SVG[key]
        renderer = _QtSvg.QSvgRenderer(QtCore.QByteArray(svg))
        sz       = renderer.defaultSize()
        lw       = tip_width
        lh       = int(tip_width * sz.height() / sz.width()) if sz.width() > 0 else tip_width
        pm       = _render_svg(svg, lw, lh)
    else:
        pm = _get_pm(key)
    if pm is None:
        return
    widget.setProperty("_svgtip_pm",  pm)
    widget.setProperty("_svgtip_cap", caption)
    widget.installEventFilter(_SvgTip.get())


# ── dialog ────────────────────────────────────────────────────────────────────

class TrackAssemblyDialog(QtWidgets.QDialog):

    def __init__(self, base_obj):
        super().__init__(FreeCADGui.getMainWindow())
        self.base_obj    = base_obj
        self.left_joint  = None
        self.right_joint = None
        self.setWindowTitle("Track Assembly Builder  v1")
        self.setWindowFlags(QtCore.Qt.Window | QtCore.Qt.WindowStaysOnTopHint)
        self._build_ui()
        self._update_computed()
        self._validate()

    # ── UI ────────────────────────────────────────────────────────────────────

    def _build_ui(self):
        root = QtWidgets.QVBoxLayout(self)
        root.setSpacing(8)

        # selected link
        obj_grp = QtWidgets.QGroupBox("Track link element")
        ol = QtWidgets.QHBoxLayout(obj_grp)
        ol.addWidget(QtWidgets.QLabel(
            "<b>{}</b>".format(self.base_obj.Label if self.base_obj else "none")
        ))
        root.addWidget(obj_grp)

        root.addWidget(self._banner(
            "<b>How to pick a joint:</b><br>"
            "① Click a circular hole <b>edge</b> in the 3-D view  (turns orange)<br>"
            "② Click the matching <b>Pick</b> button below"
        ))

        # ── joint pickers ─────────────────────────────────────────────────────
        joints_grp = QtWidgets.QGroupBox("Joint connection points")
        jv = QtWidgets.QVBoxLayout(joints_grp)
        jg = QtWidgets.QGridLayout()
        jg.setColumnStretch(1, 1)

        self.left_icon   = QtWidgets.QLabel("○"); self.left_icon.setFixedWidth(20)
        self.left_coords = QtWidgets.QLabel("<i>not picked</i>")
        self.btn_left    = QtWidgets.QPushButton("⬅  Pick Left Joint")
        self.btn_left.setToolTip("① Click hole edge in 3-D view  ② click here")
        _attach_svg_tip(self.btn_left, _SVG_LINK, 300, 88,
                        "① Click the circular hole edge in the 3-D view\n"
                        "② Click this button to record it\n"
                        "Pitch = distance between left and right joint centres")
        self.btn_left.clicked.connect(self._on_pick_left)

        self.right_icon   = QtWidgets.QLabel("○"); self.right_icon.setFixedWidth(20)
        self.right_coords = QtWidgets.QLabel("<i>not picked</i>")
        self.btn_right    = QtWidgets.QPushButton("Pick Right Joint  ➡")
        self.btn_right.setToolTip("① Click hole edge in 3-D view  ② click here")
        _attach_svg_tip(self.btn_right, _SVG_LINK, 300, 88,
                        "① Click the circular hole edge in the 3-D view\n"
                        "② Click this button to record it\n"
                        "Pitch = distance between left and right joint centres")
        self.btn_right.clicked.connect(self._on_pick_right)

        jg.addWidget(self.left_icon,    0, 0)
        jg.addWidget(self.left_coords,  0, 1)
        jg.addWidget(self.btn_left,     0, 2)
        jg.addWidget(self.right_icon,   1, 0)
        jg.addWidget(self.right_coords, 1, 1)
        jg.addWidget(self.btn_right,    1, 2)
        jv.addLayout(jg)
        root.addWidget(joints_grp)

        root.addWidget(self._hsep())

        # ── loop direction ─────────────────────────────────────────────────────
        dir_grp = QtWidgets.QGroupBox("Loop direction")
        dir_lay = QtWidgets.QHBoxLayout(dir_grp)
        self.radio_up   = QtWidgets.QRadioButton("↑  Up   (CCW)")
        self.radio_down = QtWidgets.QRadioButton("↓  Down  (CW)")
        self.radio_up.setChecked(True)
        for rb in (self.radio_up, self.radio_down):
            _attach_svg_tip(rb, _SVG_DIR,
                            caption="Up (CCW): arc above straights\nDown (CW): arc below straights")
        dir_lay.addWidget(self.radio_up)
        dir_lay.addWidget(self.radio_down)
        root.addWidget(dir_grp)

        root.addWidget(self._hsep())

        # ── wheel parameters ───────────────────────────────────────────────────
        wheel_grp = QtWidgets.QGroupBox("Wheel parameters")
        wv = QtWidgets.QVBoxLayout(wheel_grp)
        wf = QtWidgets.QFormLayout()
        wv.addLayout(wf)

        self.spin_D = QtWidgets.QDoubleSpinBox()
        self.spin_D.setRange(1.0, 99999.0); self.spin_D.setDecimals(3)
        self.spin_D.setSuffix(" mm"); self.spin_D.setValue(25.0)
        self.spin_D.setToolTip("Outer wheel diameter  (drives N per arc)")
        _attach_svg_tip(self.spin_D, _SVG_WHEEL, 300, 132,
                        "Outer diameter D — chain rides on this edge\n"
                        "Larger D → fewer links per arc → gentler curve")
        self.spin_D.valueChanged.connect(self._on_param_changed)
        wf.addRow("Wheel diameter D:", self.spin_D)

        self.spin_W = QtWidgets.QDoubleSpinBox()
        self.spin_W.setRange(0.1, 9999.0); self.spin_W.setDecimals(3)
        self.spin_W.setSuffix(" mm"); self.spin_W.setValue(26.0)
        self.spin_W.setToolTip("Wheel width along axle axis  (≥ chain inner width)")
        _attach_svg_tip(self.spin_W, _SVG_WHEEL, 300, 132,
                        "Width W — should be ≥ chain inner width")
        self.spin_W.valueChanged.connect(self._on_param_changed)
        wf.addRow("Wheel width W:", self.spin_W)

        self.spin_hub = QtWidgets.QDoubleSpinBox()
        self.spin_hub.setRange(0.0, 9999.0); self.spin_hub.setDecimals(3)
        self.spin_hub.setSuffix(" mm"); self.spin_hub.setValue(2.0)
        self.spin_hub.setToolTip("Hub bore diameter  (0 = solid, must be < D)")
        _attach_svg_tip(self.spin_hub, _SVG_WHEEL, 300, 132,
                        "Hub bore ⌀ — central axle hole\n0 = solid wheel  ·  must be < D")
        self.spin_hub.valueChanged.connect(self._on_param_changed)
        wf.addRow("Hub bore ⌀:", self.spin_hub)
        wf.addRow("", self._hint("0 = solid wheel  ·  must be < D"))

        self.spin_H = QtWidgets.QDoubleSpinBox()
        self.spin_H.setRange(0.1, 9999.0); self.spin_H.setDecimals(3)
        self.spin_H.setSuffix(" mm"); self.spin_H.setValue(6.0)
        self.spin_H.setToolTip("Link body height  (sets polygon face depth)")
        _attach_svg_tip(self.spin_H, _SVG_H, 280, 90,
                        "Link body height H\n"
                        "Polygon apothem = R·cos(π/2n) − H/2\n"
                        "so the link inner face sits flush on each polygon face")
        self.spin_H.valueChanged.connect(self._on_param_changed)
        wf.addRow("Link body height H:", self.spin_H)
        wf.addRow("", self._hint("thickness of one link body  ·  sets polygon face depth"))

        self.check_sym = QtWidgets.QCheckBox("Symmetric  (centred on Z = 0)")
        self.check_sym.setChecked(True)
        self.check_sym.setToolTip("Symmetric: centred on Z=0 (W/2 each side)  ·  Unchecked: starts at Z=0 extends +W")
        _attach_svg_tip(self.check_sym, _SVG_SYM, 300, 110,
                        "Checked: wheel centred on Z=0 (W/2 each side)\n"
                        "Unchecked: wheel starts at Z=0, extends W in +Z")
        wf.addRow("", self.check_sym)

        root.addWidget(wheel_grp)

        root.addWidget(self._hsep())

        # ── chain parameters ───────────────────────────────────────────────────
        chain_grp = QtWidgets.QGroupBox("Chain parameters")
        cf = QtWidgets.QFormLayout(chain_grp)

        self.spin_dist = QtWidgets.QDoubleSpinBox()
        self.spin_dist.setRange(0.0, 999999.0); self.spin_dist.setDecimals(2)
        self.spin_dist.setSuffix(" mm"); self.spin_dist.setValue(70.0)
        self.spin_dist.setToolTip("Minimum centre-to-centre wheel distance  (0 = pure circle)")
        _attach_svg_tip(self.spin_dist, _SVG_DIST, 300, 90,
                        "Minimum centre-to-centre wheel distance\n"
                        "Rounded up to whole links  ·  0 = pure circle")
        self.spin_dist.valueChanged.connect(self._on_param_changed)
        cf.addRow("Min wheel distance:", self.spin_dist)
        cf.addRow("", self._hint("centre-to-centre  ·  0 = pure circle"))

        root.addWidget(chain_grp)

        # ── computed panel ─────────────────────────────────────────────────────
        comp_grp = QtWidgets.QGroupBox("Computed")
        comp_grp.setStyleSheet(
            "QGroupBox { background:#f0f4f8; border-radius:4px; margin-top:6px; }"
            "QGroupBox::title { subcontrol-origin:margin; subcontrol-position:top left;"
            " padding:0 4px; }"
        )
        cfl = QtWidgets.QFormLayout(comp_grp)

        self.lbl_pitch      = QtWidgets.QLabel("—")
        self.lbl_n_arc      = QtWidgets.QLabel("—")
        self.lbl_n_straight = QtWidgets.QLabel("—")
        self.lbl_n_total    = QtWidgets.QLabel("—")
        self.lbl_diameter     = QtWidgets.QLabel("—")
        self.lbl_apothem    = QtWidgets.QLabel("—")
        self.lbl_straight   = QtWidgets.QLabel("—")

        cfl.addRow("Pitch:",                 self.lbl_pitch)
        cfl.addRow("N per arc:",             self.lbl_n_arc)
        cfl.addRow("N straight per side:",   self.lbl_n_straight)
        cfl.addRow("Total links:",           self.lbl_n_total)
        cfl.addRow("N-gon outer ⌀:",         self.lbl_diameter)
        cfl.addRow("Polygon face depth:",    self.lbl_apothem)
        cfl.addRow("Actual wheel distance:", self.lbl_straight)

        root.addWidget(comp_grp)

        root.addWidget(self._hsep())

        # ── what to generate ───────────────────────────────────────────────────
        gen_grp = QtWidgets.QGroupBox("Generate")
        gh = QtWidgets.QHBoxLayout(gen_grp)
        self.check_chain       = QtWidgets.QCheckBox("Chain")
        self.check_wheel_left  = QtWidgets.QCheckBox("Left wheel")
        self.check_wheel_right = QtWidgets.QCheckBox("Right wheel")
        self.check_chain.setToolTip(
            "Generate the chain compound:\n"
            "N copies of the selected link body placed around the oval.")
        self.check_wheel_left.setToolTip(
            "Generate the left wheel cylinder.\n"
            "Placed at the left arc centre.")
        self.check_wheel_right.setToolTip(
            "Generate the right wheel cylinder.\n"
            "Placed at the right arc centre.")
        for cb in (self.check_chain, self.check_wheel_left, self.check_wheel_right):
            cb.setChecked(True)
            gh.addWidget(cb)
        gh.addStretch()
        root.addWidget(gen_grp)

        # ── buttons ────────────────────────────────────────────────────────────
        btn_row = QtWidgets.QHBoxLayout()
        self.gen_btn = QtWidgets.QPushButton("Generate Assembly")
        self.gen_btn.setDefault(True)
        self.gen_btn.setEnabled(False)
        self.gen_btn.clicked.connect(self._on_generate)
        cancel_btn = QtWidgets.QPushButton("Cancel")
        cancel_btn.clicked.connect(self.reject)
        btn_row.addStretch()
        btn_row.addWidget(cancel_btn)
        btn_row.addWidget(self.gen_btn)
        root.addLayout(btn_row)

        self.setMinimumWidth(480)

    # ── helpers ───────────────────────────────────────────────────────────────

    def _banner(self, html):
        lbl = QtWidgets.QLabel(html)
        lbl.setStyleSheet(
            "background:#fffbe6; border:1px solid #f0c040;"
            "border-radius:4px; padding:6px;")
        lbl.setWordWrap(True)
        return lbl

    def _hint(self, txt):
        lbl = QtWidgets.QLabel(txt)
        lbl.setStyleSheet("color:gray; font-size:10px;")
        lbl.setWordWrap(True)
        return lbl

    def _hsep(self):
        sep = QtWidgets.QFrame()
        sep.setFrameShape(QtWidgets.QFrame.HLine)
        sep.setFrameShadow(QtWidgets.QFrame.Sunken)
        return sep

    # ── joint picking ─────────────────────────────────────────────────────────

    def _read_circle(self):
        for item in FreeCADGui.Selection.getSelectionEx():
            for sub in item.SubObjects:
                if hasattr(sub, "Curve") and hasattr(sub.Curve, "Center"):
                    c = sub.Curve.Center
                    return FreeCAD.Vector(c.x, c.y, c.z)
        return None

    def _fmt(self, v):
        return "({:.2f},  {:.2f},  {:.2f})".format(v.x, v.y, v.z)

    def _warn_no_circle(self):
        QtWidgets.QMessageBox.warning(
            self, "No circular edge selected",
            "No circular edge found in the current selection.\n\n"
            "• Click directly on the rim of the hole (not the flat face)\n"
            "• The edge turns orange when selected\n"
            "• Then click the Pick button"
        )

    def _on_pick_left(self):
        c = self._read_circle()
        if c is None:
            self._warn_no_circle(); return
        self.left_joint = c
        self.left_icon.setText("✅")
        self.left_coords.setText(self._fmt(c))
        self._on_param_changed()

    def _on_pick_right(self):
        c = self._read_circle()
        if c is None:
            self._warn_no_circle(); return
        self.right_joint = c
        self.right_icon.setText("✅")
        self.right_coords.setText(self._fmt(c))
        self._on_param_changed()

    def _on_param_changed(self, _=None):
        self._update_computed()
        self._validate()

    # ── math ──────────────────────────────────────────────────────────────────

    def _pitch(self):
        j1, j2 = self.left_joint, self.right_joint
        if j1 is None or j2 is None:
            return None
        return math.sqrt((j2.x-j1.x)**2 + (j2.y-j1.y)**2)

    def _n_per_arc(self, pitch, D):
        arg = pitch / D
        if arg >= 1.0:
            return None
        return max(2, round(math.pi / (2.0 * math.asin(arg))))

    # ── computed labels ───────────────────────────────────────────────────────

    def _n_straight(self, p):
        dist = self.spin_dist.value()
        if dist <= 0.0 or p <= 0.0:
            return 0
        return math.ceil(dist / p)

    def _update_computed(self):
        p = self._pitch()
        if p is None:
            for lbl in (self.lbl_pitch, self.lbl_n_arc, self.lbl_n_straight,
                        self.lbl_n_total, self.lbl_diameter, self.lbl_apothem,
                        self.lbl_straight):
                lbl.setText("—")
            return

        D     = self.spin_D.value()
        h_seg = self.spin_H.value() / 2.0
        Ns    = self._n_straight(p)

        self.lbl_pitch.setText("<b>{:.4f} mm</b>".format(p))

        n = self._n_per_arc(p, D)
        if n is None:
            msg = "<i style='color:red'>diameter too small for this pitch</i>"
            for lbl in (self.lbl_n_arc, self.lbl_n_straight, self.lbl_n_total,
                        self.lbl_diameter, self.lbl_apothem, self.lbl_straight):
                lbl.setText(msg)
            return

        N          = 2 * n + 2 * Ns
        radius     = p / (2.0 * math.sin(math.pi / (2.0 * n)))
        half_angle = math.pi / (2 * n)
        apothem    = radius * math.cos(half_angle) - h_seg
        R_poly     = apothem / math.cos(half_angle)
        s_len      = Ns * p

        self.lbl_n_arc.setText("<b>{}</b>  links per arc".format(n))
        self.lbl_n_straight.setText("<b>{}</b>  links per side".format(Ns))
        self.lbl_n_total.setText("<b>{}</b>  links".format(N))
        self.lbl_diameter.setText(
            "<b>{:.3f} mm</b>  →  {}-gon wheel".format(2.0 * R_poly, 2 * n))
        self.lbl_apothem.setText(
            "<b>{:.3f} mm</b>  (R·cos(π/2n) − H/2)".format(apothem))
        self.lbl_straight.setText(
            "<b>{:.3f} mm</b>  ({} × pitch)".format(s_len, Ns))

    # ── validation ────────────────────────────────────────────────────────────

    def _validate(self):
        p = self._pitch()
        ok = True
        if p is None:
            ok = False
        else:
            D   = self.spin_D.value()
            hub = self.spin_hub.value()
            if self._n_per_arc(p, D) is None:
                ok = False
            elif hub >= D:
                ok = False
        self.gen_btn.setEnabled(ok)
        return ok

    # ── wheel body (PartDesign) ───────────────────────────────────────────────

    def _make_wheel_body(self, label, n, pitch, W, hub_bore, h_seg, symmetric, cx, cy):
        """Create a PartDesign::Body with a sketch + pad so the user can keep
        editing the wheel in the normal parametric workflow.

        Profile: regular 2n-gon with optional bore circle in the same sketch.
        Sketch placed at (cx, cy, z_offset) facing +Z.
        symmetric=True  → z_offset = −W/2  (wheel centred on Z=0)
        symmetric=False → z_offset =  0    (wheel starts at Z=0, extends +W)
        """
        doc = FreeCAD.ActiveDocument

        R          = pitch / (2.0 * math.sin(math.pi / (2.0 * n)))
        Rb         = hub_bore / 2.0
        n_sides    = 2 * n
        half_angle = math.pi / n_sides
        link_mid_r = R * math.cos(half_angle)
        apothem    = link_mid_r - h_seg
        R_poly     = apothem / math.cos(half_angle)
        z_offset   = -W / 2.0 if symmetric else 0.0

        body   = doc.addObject("PartDesign::Body",       label)
        sketch = doc.addObject("Sketcher::SketchObject", label + "_Sketch")
        body.addObject(sketch)

        sketch.Placement = FreeCAD.Placement(
            FreeCAD.Vector(cx, cy, z_offset),
            FreeCAD.Rotation()          # XY plane, +Z normal
        )

        # polygon outline (local coords — origin = wheel centre)
        for i in range(n_sides):
            a0 = math.radians(-90.0 + i       * 360.0 / n_sides)
            a1 = math.radians(-90.0 + (i + 1) * 360.0 / n_sides)
            sketch.addGeometry(Part.LineSegment(
                FreeCAD.Vector(R_poly * math.cos(a0), R_poly * math.sin(a0), 0),
                FreeCAD.Vector(R_poly * math.cos(a1), R_poly * math.sin(a1), 0)
            ))

        # bore circle (inner loop → Pad treats it as a through-hole)
        if Rb > 0.001:
            sketch.addGeometry(
                Part.Circle(FreeCAD.Vector(0, 0, 0), FreeCAD.Vector(0, 0, 1), Rb)
            )

        pad = doc.addObject("PartDesign::Pad", label + "_Pad")
        body.addObject(pad)
        pad.Profile = sketch
        pad.Length  = W
        body.Tip    = pad

        return body

    # ── generate ──────────────────────────────────────────────────────────────

    def _on_generate(self):
        if not self._validate():
            return

        j1  = self.left_joint
        j2  = self.right_joint
        p   = self._pitch()
        D   = self.spin_D.value()
        W   = self.spin_W.value()
        hub   = self.spin_hub.value()
        h_seg = self.spin_H.value() / 2.0
        Ns    = self._n_straight(p)
        Ddir = +1.0 if self.radio_up.isChecked() else -1.0

        n       = self._n_per_arc(p, D)
        N       = 2 * n + 2 * Ns
        radius  = p / (2.0 * math.sin(math.pi / (2.0 * n)))
        half_sl = Ns * p / 2.0

        cx    = (j1.x + j2.x) / 2.0
        cy    = (j1.y + j2.y) / 2.0
        cz    = (j1.z + j2.z) / 2.0
        e_ang = math.degrees(math.atan2(j2.y - j1.y, j2.x - j1.x))

        doc     = FreeCAD.ActiveDocument
        created = []

        # ── chain ─────────────────────────────────────────────────────────────
        if self.check_chain.isChecked():
            base_shape = self.base_obj.Shape

            def _mat(tx, ty_raw, chain_deg_raw):
                ty        = Ddir * ty_raw
                chain_deg = Ddir * chain_deg_raw
                a  = math.radians(chain_deg - e_ang)
                ca, sa = math.cos(a), math.sin(a)
                m = FreeCAD.Matrix()
                m.A11 = ca;  m.A12 = -sa; m.A13 = 0; m.A14 = tx - ca*cx + sa*cy
                m.A21 = sa;  m.A22 =  ca; m.A23 = 0; m.A24 = ty - sa*cx - ca*cy
                m.A31 =  0;  m.A32 =   0; m.A33 = 1; m.A34 = 0
                m.A41 =  0;  m.A42 =   0; m.A43 = 0; m.A44 = 1
                return m

            shapes = []
            aS = 180.0 / n

            def _add(tx, ty, deg):
                s = base_shape.copy()
                s.transformShape(_mat(tx, ty, deg))
                shapes.append(s)

            # bottom straight  →
            for i in range(Ns):
                _add(-half_sl + p/2 + i*p, -radius, 0.0)

            # right arc  (−90° → +90°)
            for i in range(n):
                phi0 = math.radians(-90.0 +  i      * aS)
                phi1 = math.radians(-90.0 + (i + 1) * aS)
                px0 = half_sl + radius * math.cos(phi0); py0 = radius * math.sin(phi0)
                px1 = half_sl + radius * math.cos(phi1); py1 = radius * math.sin(phi1)
                _add((px0+px1)/2, (py0+py1)/2,
                     math.degrees(math.atan2(py1-py0, px1-px0)))

            # top straight  ←
            for i in range(Ns):
                _add(half_sl - p/2 - i*p, radius, 180.0)

            # left arc  (+90° → +270°)
            for i in range(n):
                phi0 = math.radians(90.0 +  i      * aS)
                phi1 = math.radians(90.0 + (i + 1) * aS)
                px0 = -half_sl + radius * math.cos(phi0); py0 = radius * math.sin(phi0)
                px1 = -half_sl + radius * math.cos(phi1); py1 = radius * math.sin(phi1)
                _add((px0+px1)/2, (py0+py1)/2,
                     math.degrees(math.atan2(py1-py0, px1-px0)))

            compound = Part.makeCompound(shapes)
            feat = doc.addObject("Part::Feature", "TrackChain")
            feat.Shape = compound
            feat.Label = "TrackChain_{}links_{}".format(
                N, "up" if Ddir > 0 else "down")
            created.append(feat.Label)

        # ── wheels ────────────────────────────────────────────────────────────
        sym = self.check_sym.isChecked()
        for side, wx in (("Left", -half_sl), ("Right", half_sl)):
            cb = self.check_wheel_left if side == "Left" else self.check_wheel_right
            if not cb.isChecked():
                continue
            label = "Wheel_{}_{}-gon".format(side, 2 * n)
            try:
                self._make_wheel_body(label, n, p, W, hub, h_seg, sym, wx, 0.0)
            except Exception as e:
                QtWidgets.QMessageBox.critical(self, "Wheel Error", str(e))
                return
            created.append(label)

        doc.recompute()

        try:
            FreeCADGui.ActiveDocument.activeView().viewTop()
            FreeCADGui.SendMsgToActiveView("ViewFit")
        except Exception:
            pass

        self.accept()

        QtWidgets.QMessageBox.information(
            None, "Track Assembly  –  Done",
            "Assembly created!\n\n"
            "  Pitch             : {:.4f} mm\n"
            "  N per arc         : {}\n"
            "  Total links       : {}\n"
            "  Straight / side   : {} links  (actual {:.2f} mm)\n"
            "  Wheel shape       : {}-gon  (circumradius {:.3f} mm)\n"
            "  Wheel width       : {:.3f} mm\n"
            "  Direction         : {}\n\n"
            "Objects created:\n{}".format(
                p, n, N, Ns, Ns*p, 2*n, radius, W,
                "Up (CCW)" if Ddir > 0 else "Down (CW)",
                "\n".join("  • " + lbl for lbl in created)
            )
        )


# ── entry point ───────────────────────────────────────────────────────────────

def run():
    try:
        from PySide2 import QtWidgets, QtCore
    except ImportError:
        from PySide import QtGui as QtWidgets, QtCore

    if not FreeCAD.ActiveDocument:
        QtWidgets.QMessageBox.warning(
            None, "Track Assembly",
            "No active document.\nCreate or open a FreeCAD document first."
        )
        return

    sel = FreeCADGui.Selection.getSelection()
    if not sel:
        QtWidgets.QMessageBox.warning(
            None, "Track Assembly",
            "Select the track-link body in the 3-D view first,\nthen run the macro."
        )
        return

    dlg = TrackAssemblyDialog(sel[0])
    dlg.show()

    loop = QtCore.QEventLoop()
    dlg.finished.connect(loop.quit)
    loop.exec_()


run()
