# -*- coding: utf-8 -*-
"""
CableSpool.FCMacro  -  parametric stadium-shaped cable spool for FreeCAD

Body     : stadium (rectangle + semicircle ends), extruded in Z
Side     : helical groove the cable snaps into (constant pitch)
Ends     : first/last loop continue into a ramp "corridor" that climbs to the
           bottom/top face, and there the groove keeps running round while
           tightening inward - the way the last turn of a wound cable does - so
           it ends up on the inside of the wall with no corner to kink the
           cable. Draw your USB-C connector pocket on the face where that run
           ends (markers "Anchor_Bottom" / "Anchor_Top" show where).

Output   : PartDesign Body "CableSpool" (base shape inside) -> sketch on the
           top/bottom face and Pocket your connector shape directly.

Edit the parameters below, then run the macro again (it builds a new set).
All dimensions in mm.
"""

import math
import FreeCAD as App
import Part

# ============================ PARAMETERS ============================
CABLE_LENGTH        = 1500.0  # total cable length incl. connectors
CABLE_DIAMETER      = 3.5     # MEASURE your cable with calipers
CLEARANCE           = 0.3     # added to cable diameter for the groove
GROOVE_DEPTH_FAC    = 0.85    # groove depth / groove diameter
                              #   <0.5 = shallow cradle, the cable sits proud
                              #   0.5  = half open, widest opening there is
                              #   0.8-0.9 = undercut, snaps in. Must stay < 1.0
MIN_WALL            = 1.2     # plastic rib between neighbouring turns

WIDTH               = 40.0    # outer width  (= diameter of the round ends)
LENGTH              = 75.0    # outer length (>= WIDTH)
HEIGHT              = 0.0     # 0 = auto from cable length
                              # >0 = fixed height, pitch is adapted

FACE_CLEAR          = 0.0     # material between the face channel and the first
                              # spiral turn above it; 0 = use MIN_WALL. Worth
                              # raising on its own - the wall between two turns
                              # is loaded quite differently from the roof over
                              # the channel, which is where the two would meet
END_MARGIN          = 0.0     # face -> centre of first/last turn, 0 = auto
RAMP_LENGTH         = 25.0    # length along perimeter used to climb to face
FACE_TURN           = 0.1     # after the ramp reaches the face the groove turns
                              # inward for at least this many laps, then strikes
                              # out straight across the face. The turn-in is
                              # stretched past this to wherever that straight
                              # comes out longest. 0 = stop at the wall
FACE_INSET          = 0.0     # how far inward the groove moves over that run;
                              # 0 = auto (just clears the outer wall)
FACE_DEPTH          = 0.0     # depth of face channel, 0 = groove diameter
CONNECTOR_DEPTH     = 0.0     # how deep the connector pocket has to be cut
                              # (plug thickness). Deeper than the face channel
                              # and the pocket has to sit over the solid core,
                              # clear of the groove in the wall - the exit is
                              # then aimed to make that so. 0 = don't care
CONNECTOR_WIDTH     = 14.0    # width the connector pocket needs kept clear -
                              # the face channel's exit angle is chosen to make
                              # the clear corridor of this width as long as it
                              # can be
CONNECTOR_ALLOWANCE = 20.0    # clear run kept at the end of the face channel
                              # for the connector - the channel stops this far
                              # short of the far side and you sketch the pocket
                              # into it. Lower it and the channel runs further.
EDGE_FILLET         = 1.5     # top/bottom outer edge fillet, 0 = none
SLOT_EPS            = 0.05    # face slot is this much wider than the
                              # groove, to keep its walls off the tube
SAMPLE_STEP         = 3.0     # ramp sampling step (smaller = smoother, slower);
                              # the spiral itself is exact geometry

USE_DIALOG          = True    # ask for values at start (remembers last input)
# ====================================================================

V = App.Vector


def log(msg):
    App.Console.PrintMessage("[CableSpool] " + msg + "\n")


def warn(msg):
    App.Console.PrintWarning("[CableSpool] " + msg + "\n")


# The face channel is swung onto a diagonal before it runs out across the face.
# It cannot simply carry on along its tangent - a tangent to the turn-in points
# along the perimeter, so it meets the wall within a dozen mm - so a release arc
# puts it on a heading somewhere in this range, whichever leaves the longest
# clear corridor for the connector.
FACE_EXIT_ANGLE = (10.0, 55.0)
FACE_BEND = 12.0                        # radius of that release arc


def poly_len(pts):
    return sum(math.hypot(pts[i + 1][0] - pts[i][0], pts[i + 1][1] - pts[i][1])
               for i in range(len(pts) - 1))


def face_stadium_pt(geo, u, t, span=0.0):
    """point on the inward-turning face path, t = 0 at the ramp, 1 at the end.

    The inward move finishes within geo["trans"] and the run then holds that
    depth. Easing it over the whole run instead leaves it hugging the wall at
    the start, where it is still cutting the rim - on one reported spool that
    was 60% of the run with the outer wall breached."""
    S, r, P, inset = geo["S"], geo["r"], geo["P"], geo["inset"]
    u = u % P
    if u < S:
        x, y = u, -r
    elif u < S + math.pi * r:
        a = -math.pi / 2 + (u - S) / r
        x, y = S + r * math.cos(a), r * math.sin(a)
    elif u < 3 * S + math.pi * r:
        x, y = S - (u - S - math.pi * r), r
    elif u < 3 * S + 2 * math.pi * r:
        a = math.pi / 2 + (u - 3 * S - math.pi * r) / r
        x, y = -S + r * math.cos(a), r * math.sin(a)
    else:
        x, y = -S + (u - 3 * S - 2 * math.pi * r), -r
    vx, vy = max(-S, min(S, x)) - x, -y
    n = math.hypot(vx, vy) or 1.0
    trans = geo.get("trans") or 0.0
    f = t * span / trans if trans > 0 and span > 0 else t
    f = max(0.0, min(1.0, f))
    o = inset * f * f * (3 - 2 * f)
    return x + vx / n * o, y + vy / n * o


def face_turn_length(geo, u_start, sgn, span):
    """length of the turned-in part of a face run"""
    if span <= 0:
        return 0.0
    total, prev, n = 0.0, None, 48
    for i in range(n + 1):
        t = i / float(n)
        cur = face_stadium_pt(geo, u_start + sgn * t * span, t, span)
        if prev is not None:
            total += math.hypot(cur[0] - prev[0], cur[1] - prev[1])
        prev = cur
    return total


def face_plan(geo, u_start, sgn, spans=None, collect=False):
    """Where a face run goes, as a pure function of the numbers - the dialog
    preview and the build both call this, so they cannot drift apart.

    The run turns inward along the perimeter, is swung by a FACE_BEND arc onto a
    diagonal, and finally runs straight across the open face. That straight is
    the connector's room; wrapping on round the outline instead just parcels the
    pocket up in more channel, and carrying on along the tangent does not work
    either - a tangent to the turn-in runs along the perimeter and meets the
    wall within a dozen mm.

    Both where the turn-in stops and which heading it is swung onto are chosen
    together, for the longest clear corridor CONNECTOR_WIDTH wide - that is the
    space a connector actually occupies, and measuring a bare centre line
    instead picks headings that run down a lane with the channel alongside.

    With `collect`, every turn-in length tried is returned instead of just the
    winner, as (span, arc_pts, dir, tail_len, room) - that is what lets the two
    ends be traded off against the cable budget.

    Returns (span, arc_pts, (dx, dy), tail_len); arc_pts walks the release arc
    from the end of the turn-in to where the straight begins."""
    S, r, P = geo["S"], geo["r"], geo["P"]
    lim = geo["WIDTH"] / 2.0 - geo["R"] - geo["MIN_WALL"]
    base, bend = geo["turn"] * P, geo["bend"]
    half = geo["width"] / 2.0
    clear = geo["d"] + geo["MIN_WALL"]      # channel-to-channel spacing
    # A pocket cut deeper than the face channel has to land over the solid
    # core; outside r - R there is the groove in the wall under it, and the
    # pocket would break into it. Nothing used to enforce this - the exit
    # happened to land over solid material by about a millimetre.
    core = geo.get("core")
    if base <= 0:
        return [] if collect else (base, [], (0.0, 0.0), 0.0)

    def outside(x, y):
        return math.hypot(x - max(-S, min(S, x)), y) > lim

    # channel centre-line to the side of a pocket, and the outer limit a
    # pocket side may reach (wall rib plus the edge fillet)
    edge = geo["R"] + SLOT_EPS + geo["MIN_WALL"]
    lim_pocket = geo["WIDTH"] / 2.0 - max(geo["MIN_WALL"], 0.8) - EDGE_FILLET

    def pocket_out(x, y):
        dd = math.hypot(x - max(-S, min(S, x)), y)
        return dd > lim_pocket or (core is not None and dd > core)

    def try_run(span, laid, ex, ey, dx, dy, deg):
        a = math.radians(deg)
        tx = math.cos(a) * (1.0 if ex <= 0 else -1.0)
        ty = math.sin(a) * (1.0 if ey <= 0 else -1.0)
        theta = math.atan2(dx * ty - dy * tx, dx * tx + dy * ty)
        pts = [(ex, ey)]
        if bend > 1e-6 and abs(theta) > 1e-4:
            nx, ny = (-dy, dx) if theta > 0 else (dy, -dx)
            cx, cy = ex + bend * nx, ey + bend * ny
            for i in range(1, 13):
                w = theta * i / 12.0
                cw, sw = math.cos(w), math.sin(w)
                rx, ry = ex - cx, ey - cy
                px, py = cx + rx * cw - ry * sw, cy + rx * sw + ry * cw
                if outside(px, py) or any(
                        (px - qx) ** 2 + (py - qy) ** 2 < clear * clear
                        for qx, qy in laid):
                    return None
                pts.append((px, py))
        # How long a corridor CONNECTOR_WIDTH wide stays clear. The channel
        # already laid on this face is what normally ends it, so test it in
        # the corridor's own frame: any centre-line point that sits within
        # half + edge sideways caps the length at its distance ahead. It used to
        # be sampled at 14 points over the whole run, and the corridor slipped
        # between them straight through the channel.
        px, py = pts[-1]
        nx, ny = -ty, tx
        limit = 2.0 * (geo["LENGTH"] + geo["WIDTH"])
        for qx, qy in laid:
            ahead = (qx - px) * tx + (qy - py) * ty
            side = abs((qx - px) * nx + (qy - py) * ny)
            if ahead > 0.0 and side < half + edge:
                limit = min(limit, ahead - edge)
        run, step = 0.0, 1.5
        while run + step <= limit:
            t = run + step
            cx, cy = px + tx * t, py + ty * t
            if (pocket_out(cx, cy) or pocket_out(cx + nx * half, cy + ny * half)
                    or pocket_out(cx - nx * half, cy - ny * half)):
                break
            run = t
        return pts, (tx, ty), max(0.0, run), bend * abs(theta)

    best, steps, seen = None, 40, []
    for span in (spans if spans is not None
                 else [base + P * i / steps for i in range(steps + 1)]):
        # Everything already cut into this face, densely: the part of the ramp
        # that still reaches the face, and the turn-in up to a short way
        # before the exit (that last bit is the corridor's own tail).
        m = max(16, int(span / 1.5))
        excl = half + edge + 1.5
        laid = [face_stadium_pt(geo, u_start + sgn * j / float(m) * span,
                                j / float(m), span)
                for j in range(m + 1) if (1.0 - j / float(m)) * span > excl]
        ramp = geo.get("ramp_u", 0.0)
        laid += [face_stadium_pt(geo, u_start - sgn * k * 1.5, 0.0, span)
                 for k in range(1, int(0.5 * ramp / 1.5) + 1)]
        ex, ey = face_stadium_pt(geo, u_start + sgn * span, 1.0, span)
        bx, by = face_stadium_pt(geo, u_start + sgn * span * (1 - 1e-4),
                                 1.0 - 1e-4, span)
        dx, dy = ex - bx, ey - by
        n = math.hypot(dx, dy)
        if n < 1e-9 or outside(ex, ey):
            continue
        dx, dy = dx / n, dy / n
        lo_a, hi_a = FACE_EXIT_ANGLE
        for k in range(6):
            deg = lo_a + (hi_a - lo_a) * k / 5.0
            got = try_run(span, laid, ex, ey, dx, dy, deg)
            if got is None:
                continue
            pts, dirn, free, arc_len = got
            if collect:
                seen.append((span, pts, dirn,
                             max(0.0, free - geo["allow"]), free))
            if best is None or free > best[3] + 1.0:
                best = (span, pts, dirn, free, arc_len)
    if collect:
        return seen
    if best is None:
        return base, [], (0.0, 0.0), 0.0
    return best[0], best[1], best[2], max(0.0, best[3] - geo["allow"])


def fit_runs(geo, cable, ramp3d, allow, z0, height, pitch0, plan_at):
    """Pick the two face runs and the turn count so the cable comes out right.

    The turn count cannot do this on its own: one turn costs hypot(P, pitch),
    which is within 0.1 mm of the perimeter, so a longer spiral shortens the top
    run's approach by the same amount and the two cancel. Solving on it either
    never settles or closes the budget by pinning a run somewhere that leaves a
    connector nowhere to sit.

    What does work is that each run's length is free over a whole lap, so the
    pair spans two laps and almost any turn count can be met by some
    combination. Both ends are wanted anyway - only runs that leave the
    connector its full clearance are considered - so pair them up, and among the
    pairs that close the budget keep the one with the most room to spare.

    `plan_at(u_start, sgn)` hands back the options at a phase. Returns
    (turns, pitch, bottom, len_bot, top, len_top, cable_used)."""
    P = geo["P"]

    def usable(opts):
        """runs that leave the pocket its full length; if none do, the ones
        that come closest - anything else lands the pocket at random, which
        made a longer pocket sometimes look like it fitted where a shorter
        one did not"""
        good = [o for o in opts if o[3] > 0.0]
        if good or not opts:
            return good
        most = max(o[4] for o in opts)
        return [o for o in opts if o[4] >= most - 1.0]

    none_run = (0.0, [], (0.0, 0.0), 0.0, 0.0)
    all_bots = plan_at(-geo["ramp_u"], -1.0)
    room_max = max([o[4] for o in all_bots] or [0.0])
    bots = usable(all_bots) or [none_run]
    lb = [geo["len_of"](-geo["ramp_u"], -1.0, o) for o in bots]
    roomy = max(range(len(bots)), key=lambda k: bots[k][3])

    def pitch_for(t):
        return (height - 2.0 * z0) / t if height > 0 else pitch0

    best = None
    seed = (cable - 2.0 * (ramp3d + allow) - 2.0 * lb[roomy]) \
        / math.hypot(P, pitch0)
    for step in (-0.4, -0.2, 0.0, 0.2, 0.4):
        t = seed + step
        if t < 1.0:
            continue
        per = math.hypot(P, pitch_for(t))
        u_t = t * P + geo["ramp_u"]
        tops = usable(plan_at(u_t, 1.0)) or [none_run]
        lt = [geo["len_of"](u_t, 1.0, o) for o in tops]
        target = cable - 2.0 * (ramp3d + allow) - t * per
        for i, a in enumerate(lb):
            for j, b in enumerate(lt):
                over = a + b - target
                if abs(over) > 30.0:        # far too wrong to bother scoring
                    continue
                score = (over > 0.05, round(abs(over), 1),
                         -min(bots[i][3], tops[j][3]))
                if best is None or score < best[0]:
                    best = (score, t, pitch_for(t), bots[i], a, tops[j], b,
                            2.0 * (ramp3d + allow) + a + b + t * per)
    if best is None:                        # not one pair was even close
        t = max(seed, 1.0)
        per = math.hypot(P, pitch_for(t))
        u_t = t * P + geo["ramp_u"]
        tops = usable(plan_at(u_t, 1.0)) or [none_run]
        j = max(range(len(tops)), key=lambda k: tops[k][3])
        b = geo["len_of"](u_t, 1.0, tops[j])
        best = (None, t, pitch_for(t), bots[roomy], lb[roomy], tops[j], b,
                2.0 * (ramp3d + allow) + lb[roomy] + b + t * per)
    return best[1:] + (room_max,)


# ---------------------------------------------------------------- input dialog
# (key, label, min, max, decimals, step, suffix)
DIALOG_FIELDS = [
    ("CABLE_LENGTH",        "Cable length",                 100, 10000, 0, 50,  " mm"),
    ("CABLE_DIAMETER",      "Cable diameter",               1.0, 15.0,  2, 0.1, " mm"),
    ("CLEARANCE",           "Groove clearance",             0.0, 2.0,   2, 0.05, " mm"),
    ("GROOVE_DEPTH_FAC",    "Groove depth factor (0.25-0.95)", 0.25, 0.95, 2, 0.05, ""),
    ("WIDTH",               "Spool width",                  10, 300,    1, 1,   " mm"),
    ("LENGTH",              "Spool length (>= width)",      10, 500,    1, 1,   " mm"),
    ("HEIGHT",              "Spool height (0 = auto)",      0, 500,     1, 1,   " mm"),
    ("MIN_WALL",            "Wall between turns",           0.4, 10,    2, 0.1, " mm"),
    ("FACE_CLEAR",          "Roof over face channel (0 = as wall)", 0, 10, 2, 0.1, " mm"),
    ("RAMP_LENGTH",         "Corridor ramp length",         5, 200,     1, 1,   " mm"),
    ("FACE_TURN",           "Face run (laps round the face)", 0, 2.0,  2, 0.05, ""),
    ("FACE_INSET",          "Face run inset (0 = auto)",    0, 100,    1, 0.5, " mm"),
    ("CONNECTOR_ALLOWANCE", "Connector pocket length",      0, 200,    1, 1,   " mm"),
    ("CONNECTOR_WIDTH",      "Connector pocket width",       1, 100,    1, 1,   " mm"),
    ("CONNECTOR_DEPTH",      "Connector pocket depth (0 = any)", 0, 100, 1, 1,  " mm"),
]

# which of the three schematics explains which parameter
DIAGRAM_VIEW = {
    "CABLE_DIAMETER": "section", "CLEARANCE": "section",
    "GROOVE_DEPTH_FAC": "section", "MIN_WALL": "section",
    "FACE_CLEAR": "side",
    "WIDTH": "plan", "LENGTH": "plan", "RAMP_LENGTH": "plan",
    "FACE_TURN": "plan", "FACE_INSET": "plan",
    "CONNECTOR_ALLOWANCE": "plan", "CONNECTOR_WIDTH": "plan",
    "CONNECTOR_DEPTH": "plan",
    "CABLE_LENGTH": "side", "HEIGHT": "side",
}


class Cancelled(Exception):
    pass


def qt_modules():
    try:
        from PySide6 import QtWidgets, QtGui, QtCore
    except ImportError:
        try:
            from PySide2 import QtWidgets, QtGui, QtCore
        except ImportError:
            from PySide import QtGui, QtCore
            QtWidgets = QtGui
    return QtWidgets, QtGui, QtCore


def qt_enum(owner, name, scope):
    """PySide6 nests enums in a scope class, older bindings expose them flat"""
    v = getattr(owner, name, None)
    if v is None:
        v = getattr(getattr(owner, scope), name)
    return v


def preview_geometry(v):
    """The macro's own derivation, run on whatever is in the dialog right now,
    so the diagrams and the computed line show what you are about to build.
    Returns None while the numbers are still inconsistent."""
    try:
        d = v["CABLE_DIAMETER"] + v["CLEARANCE"]
        R = d / 2.0
        depth = v["GROOVE_DEPTH_FAC"] * d
        r = v["WIDTH"] / 2.0 - depth + R
        S = max(0.0, (v["LENGTH"] - v["WIDTH"]) / 2.0)
        P = 4.0 * S + 2.0 * math.pi * r
        if r <= R or P <= 0.0:
            return None
        face_depth = FACE_DEPTH if FACE_DEPTH > 0 else d
        zb = face_depth - R
        z0 = (END_MARGIN if END_MARGIN > 0 else face_depth + R
              + (v["FACE_CLEAR"] if v["FACE_CLEAR"] > 0 else v["MIN_WALL"]))
        pitch = d + v["MIN_WALL"]
        # the build's own planner, so the preview cannot drift from it
        inset = (v["FACE_INSET"] if v["FACE_INSET"] > 0
                 else max(0.0, r - max(3.0 * d, R + v["MIN_WALL"] + 0.5)))
        inset = max(inset, (r + R + SLOT_EPS) - v["WIDTH"] / 2.0
                    + max(v["MIN_WALL"], 0.8))
        trans = math.sqrt(6.0 * inset * max(FACE_BEND, 1.0))
        geo = dict(S=S, r=r, P=P, R=R, MIN_WALL=v["MIN_WALL"],
                   WIDTH=v["WIDTH"], LENGTH=v["LENGTH"], inset=inset,
                   turn=v["FACE_TURN"], allow=v["CONNECTOR_ALLOWANCE"],
                   bend=FACE_BEND, d=d, width=v["CONNECTOR_WIDTH"],
                   trans=trans,
                   core=(r - R - v["MIN_WALL"]
                         if v["CONNECTOR_DEPTH"] > face_depth else None))
        geo["ramp_u"] = v["RAMP_LENGTH"]
        geo["len_of"] = lambda u, sg, o: (face_turn_length(geo, u, sg, o[0])
                                          + poly_len(o[1]) + o[3])
        fit = fit_runs(geo, v["CABLE_LENGTH"],
                       math.hypot(v["RAMP_LENGTH"], z0 - zb),
                       v["CONNECTOR_ALLOWANCE"], z0, v["HEIGHT"], pitch,
                       lambda u, sg: face_plan(geo, u, sg, collect=True))
        if fit is None:
            return None
        turns, pitch, bot, face_len, top, len_top, used, room_max = fit
        span, arc_pts, tail_dir, tail_len = bot[0], bot[1], bot[2], bot[3]
        H = v["HEIGHT"] if v["HEIGHT"] > 0 else 2.0 * z0 + pitch * turns
        per_end = (math.hypot(v["RAMP_LENGTH"], z0 - zb)
                   + 0.5 * (face_len + len_top) + v["CONNECTOR_ALLOWANCE"])
        return dict(d=d, R=R, depth=depth, r=r, S=S, P=P, pitch=pitch,
                    z0=z0, zb=zb, turns=turns, H=H, per_end=per_end,
                    inset=inset, face_len=face_len, span=span,
                    arc_pts=arc_pts, tail_dir=tail_dir, tail_len=tail_len,
                    pocket_max=room_max,
                    open_w=2.0 * math.sqrt(max(R * R - (depth - R) ** 2, 0.0)))
    except Exception:
        return None


def ask_values():
    QtWidgets, QtGui, QtCore = qt_modules()
    import FreeCADGui

    Qt = QtCore.Qt
    AA = qt_enum(QtGui.QPainter, "Antialiasing", "RenderHint")
    ALIGN_C = qt_enum(Qt, "AlignCenter", "AlignmentFlag")
    DASH = qt_enum(Qt, "DashLine", "PenStyle")
    NO_PEN = qt_enum(Qt, "NoPen", "PenStyle")
    NO_BRUSH = qt_enum(Qt, "NoBrush", "BrushStyle")
    FOCUS_IN = qt_enum(QtCore.QEvent, "FocusIn", "Type")
    ROUND_CAP = qt_enum(Qt, "RoundCap", "PenCapStyle")
    PT = QtCore.QPointF

    class Diagram(QtWidgets.QWidget):
        """Schematic of the parameter under the cursor, drawn to scale from the
        values currently in the dialog."""

        def __init__(self, values, parent=None):
            QtWidgets.QWidget.__init__(self, parent)
            self.values = values
            self.key = "WIDTH"
            self.setMinimumSize(430, 330)

        def set_key(self, key):
            if key != self.key:
                self.key = key
                self.update()

        # ---- painting helpers ----
        def _colours(self):
            pal = self.palette()
            ink = pal.color(qt_enum(QtGui.QPalette, "WindowText", "ColorRole"))
            hot = QtGui.QColor(226, 78, 42)
            if ink.lightness() < 128:          # light theme
                hot = QtGui.QColor(198, 52, 20)
            faint = QtGui.QColor(ink)
            faint.setAlpha(90)
            fill = QtGui.QColor(ink)
            fill.setAlpha(38)
            return ink, hot, faint, fill

        def _pen(self, col, w=1.4, style=None):
            p = QtGui.QPen(col)
            p.setWidthF(w)
            p.setCapStyle(ROUND_CAP)
            if style is not None:
                p.setStyle(style)
            return p

        def _text(self, p, x, y, s, col):
            f = p.font()
            f.setPointSizeF(max(7.0, self.font().pointSizeF() * 0.82))
            p.setFont(f)
            fm = QtGui.QFontMetricsF(f)
            w = (fm.horizontalAdvance(s) if hasattr(fm, "horizontalAdvance")
                 else fm.width(s))
            h = fm.height()
            bg = QtGui.QColor(self.palette().color(
                qt_enum(QtGui.QPalette, "Window", "ColorRole")))
            bg.setAlpha(205)
            rect = QtCore.QRectF(x - w / 2.0 - 2, y - h / 2.0, w + 4, h)
            p.setPen(NO_PEN)
            p.setBrush(bg)
            p.drawRect(rect)
            p.setBrush(NO_BRUSH)
            p.setPen(col)
            p.drawText(rect, ALIGN_C, s)

        def _arrow(self, p, tip, frm, size=5.0):
            dx, dy = tip.x() - frm.x(), tip.y() - frm.y()
            L = math.hypot(dx, dy)
            if L < 1e-6:
                return
            ux, uy = dx / L, dy / L
            for s in (1.0, -1.0):
                p.drawLine(tip, PT(tip.x() - ux * size - s * uy * size * 0.45,
                                   tip.y() - uy * size + s * ux * size * 0.45))

        def _dim(self, p, a, b, label, hot, off=12.0):
            """arrowed dimension line a->b, label offset perpendicular"""
            ink, hotc, faint, _ = self._colours()
            col = hotc if hot else faint
            dx, dy = b.x() - a.x(), b.y() - a.y()
            L = math.hypot(dx, dy)
            if L < 1e-6:
                return
            nx, ny = -dy / L, dx / L
            a2 = PT(a.x() + nx * off, a.y() + ny * off)
            b2 = PT(b.x() + nx * off, b.y() + ny * off)
            p.setPen(self._pen(col, 1.6 if hot else 1.0))
            p.drawLine(a2, b2)
            p.drawLine(a, a2)
            p.drawLine(b, b2)
            self._arrow(p, a2, b2)
            self._arrow(p, b2, a2)
            self._text(p, (a2.x() + b2.x()) / 2.0 + nx * 9,
                       (a2.y() + b2.y()) / 2.0 + ny * 9, label, col)

        # ---- the three schematics ----
        def paintEvent(self, ev):
            p = QtGui.QPainter(self)
            try:
                p.setRenderHint(AA, True)
                geo = preview_geometry(self.values())
                view = DIAGRAM_VIEW.get(self.key, "plan")
                box = QtCore.QRectF(10, 8, self.width() - 20,
                                    self.height() - 44)
                if geo is None:
                    self._text(p, self.width() / 2.0, self.height() / 2.0,
                               "check the values", self._colours()[1])
                    return
                if view == "section":
                    self._section(p, box, geo)
                elif view == "plan":
                    self._plan(p, box, geo)
                else:
                    self._side(p, box, geo)
                ink, hot, faint, _ = self._colours()
                v = self.values()
                if (v["FACE_TURN"] > 0
                        and geo["pocket_max"] < v["CONNECTOR_ALLOWANCE"]):
                    self._text(p, self.width() / 2.0, self.height() - 32,
                               "pocket does not fit - max %.0f mm at %.0f mm "
                               "wide" % (geo["pocket_max"],
                                         v["CONNECTOR_WIDTH"]), hot)
                self._text(p, self.width() / 2.0, self.height() - 14,
                           u"⌀%.2f groove · pitch %.2f · "
                           u"%.1f turns · height %.1f mm"
                           % (geo["d"], geo["pitch"], geo["turns"], geo["H"]),
                           ink)
            except Exception:
                pass
            finally:
                p.end()

        def _section(self, p, box, g):
            """wall cross-section: three turns of the snap-in groove"""
            ink, hot, faint, fill = self._colours()
            v = self.values()
            d, R, depth, pitch = g["d"], g["R"], g["depth"], g["pitch"]
            slab = depth + 4.0                      # wall thickness we show
            sc = min(box.width() * 0.42 / slab,
                     box.height() / (2.0 * pitch + d + 3.0))
            surf = box.left() + box.width() * 0.60  # the outer surface
            x_in = surf - slab * sc                 # back of the shown slab
            cy = box.center().y()
            k = self.key

            # material with the grooves taken out -> the undercut lips are real
            mat = QtGui.QPainterPath()
            mat.addRect(QtCore.QRectF(x_in, box.top(), surf - x_in,
                                      box.height()))
            centres = []
            for i in (-1, 0, 1):
                c = PT(surf - (depth - R) * sc, cy + i * pitch * sc)
                centres.append(c)
                hole = QtGui.QPainterPath()
                hole.addEllipse(c, R * sc, R * sc)
                mat = mat.subtracted(hole)
            p.setPen(self._pen(ink, 1.6))
            p.setBrush(fill)
            p.drawPath(mat)
            p.setBrush(NO_BRUSH)

            # the cable itself, so the clearance is visible as the gap
            cable = v["CABLE_DIAMETER"] / 2.0 * sc
            p.setPen(self._pen(hot if k in ("CABLE_DIAMETER", "CLEARANCE")
                               else faint, 1.3, DASH))
            p.drawEllipse(centres[1], cable, cable)

            # groove diameter, straight across the middle groove
            self._dim(p, PT(centres[1].x() - R * sc, centres[1].y()),
                      PT(centres[1].x() + R * sc, centres[1].y()),
                      u"\u2300 %.2f" % d,
                      k in ("CABLE_DIAMETER", "CLEARANCE"), off=0.0)
            if k == "CLEARANCE":
                self._text(p, centres[1].x(), centres[1].y() + cable + 11,
                           "cable %.2f + %.2f clearance"
                           % (v["CABLE_DIAMETER"], v["CLEARANCE"]), hot)

            # depth: surface -> bottom of the groove, at the groove's own height
            self._dim(p, PT(surf, centres[0].y()),
                      PT(centres[0].x() - R * sc, centres[0].y()),
                      "depth %.2f" % depth, k == "GROOVE_DEPTH_FAC", off=16.0)

            # pitch on the inside, wall thickness out in the open air
            self._dim(p, centres[0], centres[1], "pitch %.2f" % pitch,
                      k == "MIN_WALL",
                      off=(centres[0].x() - x_in) + 24.0)
            self._dim(p, PT(centres[1].x(), centres[1].y() + R * sc),
                      PT(centres[2].x(), centres[2].y() - R * sc),
                      "wall %.2f" % (pitch - d), k == "MIN_WALL",
                      off=-((surf - centres[1].x()) + 30.0))

            # how wide the groove actually opens at the surface
            half = math.sqrt(max(R * R - (depth - R) ** 2, 0.0)) * sc
            lip = k == "GROOVE_DEPTH_FAC"
            p.setPen(self._pen(hot if lip else faint, 3.0))
            p.drawLine(PT(surf, centres[2].y() - half),
                       PT(surf, centres[2].y() + half))
            self._text(p, surf + 46, centres[2].y(),
                       "opening %.2f" % g["open_w"], hot if lip else faint)
            self._text(p, (x_in + surf) / 2.0, box.top() + 9, "wall", faint)
            self._text(p, surf + 40, box.bottom() - 8, "outside", faint)

        def _plan(self, p, box, g):
            """top view: outline, and the ramp -> bend -> channel end detail"""
            ink, hot, faint, fill = self._colours()
            v = self.values()
            hw, S, r = v["WIDTH"] / 2.0, g["S"], g["r"]
            half_len = S + hw
            sc = min(box.width() / (2.0 * half_len + 26.0),
                     box.height() / (2.0 * hw + 30.0))
            cx, cy = box.center().x(), box.center().y()

            def to_px(x, y):
                return PT(cx + x * sc, cy - y * sc)

            body = QtGui.QPainterPath()
            body.addRoundedRect(
                QtCore.QRectF(cx - half_len * sc, cy - hw * sc,
                              2.0 * half_len * sc, 2.0 * hw * sc),
                hw * sc, hw * sc)
            p.setPen(self._pen(ink, 1.6))
            p.setBrush(fill)
            p.drawPath(body)
            p.setBrush(NO_BRUSH)

            P = g["P"]

            def to_inward(x, y):
                vx, vy = max(-S, min(S, x)) - x, -y
                n = math.hypot(vx, vy) or 1.0
                return vx / n, vy / n

            def stad(u):
                """centre-line point + unit tangent, same parametrisation as
                the macro's stadium_xy"""
                u = u % P
                if u < S:
                    return u, -r, 1.0, 0.0
                u -= S
                if u < math.pi * r:
                    t = -math.pi / 2 + u / r
                    return (S + r * math.cos(t), r * math.sin(t),
                            -math.sin(t), math.cos(t))
                u -= math.pi * r
                if u < 2 * S:
                    return S - u, r, -1.0, 0.0
                u -= 2 * S
                if u < math.pi * r:
                    t = math.pi / 2 + u / r
                    return (-S + r * math.cos(t), r * math.sin(t),
                            -math.sin(t), math.cos(t))
                return -S + (u - math.pi * r), -r, 1.0, 0.0

            # groove centre-line
            path = QtGui.QPainterPath()
            n = 160
            for i in range(n + 1):
                x, y, _, _ = stad(P * i / n)
                pt = to_px(x, y)
                path.moveTo(pt) if i == 0 else path.lineTo(pt)
            p.setPen(self._pen(faint, 1.0, DASH))
            p.drawPath(path)

            k = self.key
            ramp = v["RAMP_LENGTH"]
            # ramp run, still out on the wall
            rp = QtGui.QPainterPath()
            for i in range(41):
                x, y, _, _ = stad(-ramp + ramp * i / 40.0)
                pt = to_px(x, y)
                rp.moveTo(pt) if i == 0 else rp.lineTo(pt)
            p.setPen(self._pen(hot if k == "RAMP_LENGTH" else ink, 2.6))
            p.drawPath(rp)

            # face run: turns inward off the wall, then strikes out straight
            # across the open face - that straight is the connector's room
            inset, span = g["inset"], g["span"]
            hotrun = k in ("FACE_TURN", "FACE_INSET")
            ax, ay, _t1, _t2 = stad(-ramp)
            if span > 0:
                fp = QtGui.QPainterPath()
                for i in range(61):
                    t = i / 60.0
                    x, y, _, _ = stad(-ramp - t * span)
                    nx, ny = to_inward(x, y)
                    o = inset * (t * t * (3 - 2 * t))
                    ax, ay = x + nx * o, y + ny * o
                    pt = to_px(ax, ay)
                    fp.moveTo(pt) if i == 0 else fp.lineTo(pt)
                p.setPen(self._pen(hot if hotrun else ink, 2.6))
                p.drawPath(fp)
            td, tl = g["tail_dir"], g["tail_len"]
            if tl > 0:
                ex, ey = ax + td[0] * tl, ay + td[1] * tl
                p.setPen(self._pen(hot if hotrun else ink, 2.6))
                p.drawLine(to_px(ax, ay), to_px(ex, ey))
                ax, ay = ex, ey
            p.setPen(self._pen(ink, 1.0))
            p.setBrush(hot)
            p.drawEllipse(to_px(ax, ay), 3.0, 3.0)
            p.setBrush(NO_BRUSH)
            self._text(p, to_px(ax, ay).x(), to_px(ax, ay).y() - 13,
                       "anchor", faint)
            ca_len = v["CONNECTOR_ALLOWANCE"]
            if ca_len > 0 and (td[0] or td[1]):
                ex, ey = ax + td[0] * ca_len, ay + td[1] * ca_len
                p.setPen(self._pen(
                    hot if k == "CONNECTOR_ALLOWANCE" else faint, 1.8, DASH))
                p.drawLine(to_px(ax, ay), to_px(ex, ey))
                self._text(p, to_px((ax + ex) / 2.0, (ay + ey) / 2.0).x(),
                           to_px((ax + ex) / 2.0, (ay + ey) / 2.0).y() + 12,
                           "your pocket %.0f" % ca_len,
                           hot if k == "CONNECTOR_ALLOWANCE" else faint)
            if k == "RAMP_LENGTH":
                mx, my, _, _ = stad(-ramp * 0.5)
                self._text(p, to_px(mx, my).x(), to_px(mx, my).y() - 14,
                           "ramp %.0f" % ramp, hot)
            if hotrun and span > 0:
                mx, my, _, _ = stad(-ramp - span * 0.5)
                nx, ny = to_inward(mx, my)
                o = inset * 0.5
                self._text(p, to_px(mx + nx * o, my + ny * o).x(),
                           to_px(mx + nx * o, my + ny * o).y() - 14,
                           "%.2f lap in, %.1f mm, then %.0f mm straight"
                           % (span / P, inset, tl), hot)
            # overall sizes
            self._dim(p, to_px(-half_len, -hw), to_px(half_len, -hw),
                      "LENGTH %.0f" % v["LENGTH"], k == "LENGTH", off=22.0)
            self._dim(p, to_px(-half_len, -hw), to_px(-half_len, hw),
                      "WIDTH %.0f" % v["WIDTH"], k == "WIDTH", off=26.0)

        def _side(self, p, box, g):
            """side view: overall height, end margins and the turn stack"""
            ink, hot, faint, fill = self._colours()
            v = self.values()
            H, z0, pitch = g["H"], g["z0"], g["pitch"]
            wide = v["LENGTH"]
            sc = min(box.width() * 0.62 / wide, box.height() / max(H, 1.0))
            w2 = wide * sc / 2.0
            cx = box.left() + box.width() * 0.42
            base = box.bottom()

            def yz(z):
                return base - z * sc

            p.setPen(self._pen(ink, 1.6))
            p.setBrush(fill)
            p.drawRoundedRect(QtCore.QRectF(cx - w2, yz(H), 2 * w2, H * sc),
                              3.0, 3.0)
            p.setBrush(NO_BRUSH)
            # the turns
            p.setPen(self._pen(faint, 1.8))
            k = self.key
            turns = int(min(g["turns"], 60))
            for i in range(turns + 1):
                z = z0 + i * pitch
                if z > H - z0 + 1e-6:
                    break
                p.drawLine(PT(cx - w2, yz(z)), PT(cx + w2, yz(z - pitch * 0.5)))
            p.setPen(self._pen(hot if k == "CABLE_LENGTH" else ink, 2.2))
            p.drawLine(PT(cx - w2, yz(z0)), PT(cx + w2, yz(z0 - pitch * 0.5)))
            self._dim(p, PT(cx + w2, yz(0)), PT(cx + w2, yz(H)),
                      "HEIGHT %.1f" % H, k == "HEIGHT", off=-26.0)
            self._dim(p, PT(cx - w2, yz(0)), PT(cx - w2, yz(z0)),
                      "margin %.1f" % z0, False, off=22.0)
            self._text(p, cx, yz(H) - 12,
                       "%.0f mm cable → %.1f turns"
                       % (v["CABLE_LENGTH"], g["turns"]),
                       hot if k == "CABLE_LENGTH" else ink)

    class FocusWatch(QtCore.QObject):
        def __init__(self, owner, keys):
            QtCore.QObject.__init__(self, owner)
            self.keys = keys
            self.diagram = None

        def eventFilter(self, obj, ev):
            if ev.type() == FOCUS_IN and self.diagram is not None:
                key = self.keys.get(obj)
                if key:
                    self.diagram.set_key(key)
            return False

    prefs = App.ParamGet("User parameter:BaseApp/Preferences/Macros/CableSpool")
    g = globals()

    dlg = QtWidgets.QDialog(FreeCADGui.getMainWindow())
    dlg.setWindowTitle("Cable Spool parameters")
    outer = QtWidgets.QHBoxLayout(dlg)
    form = QtWidgets.QFormLayout()
    outer.addLayout(form)
    boxes = {}
    by_widget = {}
    for key, label, lo, hi, dec, step, suf in DIALOG_FIELDS:
        sb = QtWidgets.QDoubleSpinBox()
        sb.setRange(lo, hi)
        sb.setDecimals(dec)
        sb.setSingleStep(step)
        sb.setSuffix(suf)
        sb.setValue(prefs.GetFloat(key, float(g[key])))
        form.addRow(label, sb)
        boxes[key] = sb
        by_widget[sb] = key

    def current():
        return dict((k, sb.value()) for k, sb in boxes.items())

    diagram = Diagram(current, dlg)
    watch = FocusWatch(dlg, by_widget)
    watch.diagram = diagram
    for key, sb in boxes.items():
        sb.installEventFilter(watch)
        sb.valueChanged.connect(
            lambda _v, k=key: (diagram.set_key(k), diagram.update()))

    right = QtWidgets.QVBoxLayout()
    hint = QtWidgets.QLabel("Click a field - the drawing shows what it means "
                            "(to scale, from the current values).")
    hint.setWordWrap(True)
    right.addWidget(hint)
    right.addWidget(diagram, 1)
    outer.addLayout(right, 1)

    bb = QtWidgets.QDialogButtonBox(
        QtWidgets.QDialogButtonBox.Ok | QtWidgets.QDialogButtonBox.Cancel)
    bb.accepted.connect(dlg.accept)
    bb.rejected.connect(dlg.reject)
    form.addRow(bb)

    run = getattr(dlg, "exec", None) or dlg.exec_
    if not run():
        raise Cancelled("cancelled by user")
    for key, sb in boxes.items():
        g[key] = sb.value()
        prefs.SetFloat(key, sb.value())


if USE_DIALOG and App.GuiUp:
    ask_values()

# ---------------------------------------------------------------- derived
d = CABLE_DIAMETER + CLEARANCE          # groove diameter
R = d / 2.0
if not (0.25 <= GROOVE_DEPTH_FAC < 1.0):
    raise ValueError("GROOVE_DEPTH_FAC must be in [0.25, 1.0)")
if LENGTH < WIDTH:
    raise ValueError("LENGTH must be >= WIDTH")

depth = GROOVE_DEPTH_FAC * d
r = WIDTH / 2.0 - depth + R             # groove centre-line radius
S = (LENGTH - WIDTH) / 2.0              # half length of straight part
P = 4.0 * S + 2.0 * math.pi * r         # centre-line perimeter per turn
if r <= R + 2.0:
    raise ValueError("WIDTH too small for this cable")

def stadium_xy(u):
    """point + tangent on centre-line; u=0 is middle of the -Y straight side,
    running counter-clockwise (seen from top)."""
    u = u % P
    if u < S:
        return u, -r, 1.0, 0.0
    u -= S
    if u < math.pi * r:
        th = -math.pi / 2 + u / r
        return S + r * math.cos(th), r * math.sin(th), -math.sin(th), math.cos(th)
    u -= math.pi * r
    if u < 2 * S:
        return S - u, r, -1.0, 0.0
    u -= 2 * S
    if u < math.pi * r:
        th = math.pi / 2 + u / r
        return -S + r * math.cos(th), r * math.sin(th), -math.sin(th), math.cos(th)
    u -= math.pi * r
    return -S + u, -r, 1.0, 0.0


def smooth(t):
    t = max(0.0, min(1.0, t))
    return t * t * (3 - 2 * t)


def inward_dir(x, y):
    cx = max(-S, min(S, x))
    vx, vy = cx - x, -y
    n = math.hypot(vx, vy)
    return vx / n, vy / n


face_depth = FACE_DEPTH if FACE_DEPTH > 0 else d
zb = face_depth - R                     # centre z of bottom face channel
face_clear = FACE_CLEAR if FACE_CLEAR > 0 else MIN_WALL
z0 = END_MARGIN if END_MARGIN > 0 else face_depth + face_clear + R
if z0 - zb < 0.5:
    raise ValueError("END_MARGIN too small (ramp would not climb)")
if RAMP_LENGTH > 0.8 * P:
    raise ValueError("RAMP_LENGTH too long for this perimeter")

ramp3d = math.hypot(RAMP_LENGTH, z0 - zb)
# Face run: the groove does not stop at the wall and strike out for the centre -
# it keeps going round and tightens inward, the way the last turn on a wound
# cable naturally does. That leaves it sitting on the inside of the wall, on the
# face, with no corner anywhere, and that is where the connector pocket starts.
# Auto inset aims the run at the MIDDLE of the face, not just clear of the wall:
# the offset stadium collapses toward the centre segment as the inset grows, so
# a small end radius is what delivers the cable - and the connector pocket you
# draw off it - into the middle. Floor it at a radius the cable can still take.
# Auto inset aims the run at the MIDDLE of the face, not just clear of the wall:
# the offset stadium collapses toward the centre segment as the inset grows, so
# a small end radius is what delivers the cable - and the connector pocket you
# draw off it - into the middle. Floor it at a radius the cable can still take.
face_end_r = max(3.0 * d, R + MIN_WALL + 0.5)
face_inset = FACE_INSET if FACE_INSET > 0 else max(0.0, r - face_end_r)
# The channel has to get its outer edge inside the wall, with something left of
# the rim, or it simply saws the rim off along the way.
face_inset_min = (r + R + SLOT_EPS) - WIDTH / 2.0 + max(MIN_WALL, 0.8)
if FACE_TURN > 0 and face_inset < face_inset_min:
    warn("FACE_INSET %.1f mm leaves the face channel cutting the rim; "
         "using %.1f mm" % (face_inset, face_inset_min))
    face_inset = face_inset_min
# ...and it should get there promptly rather than drifting in over the whole
# run. Shortest move the cable will take: a smoothstep peaks at 6*inset/L^2 of
# curvature, so L = sqrt(6*inset*FACE_BEND) is the tightest that still respects
# the bend radius.
face_trans = math.sqrt(6.0 * face_inset * max(FACE_BEND, 1.0))
if FACE_TURN > 0 and r - face_inset <= R + MIN_WALL:
    raise ValueError("FACE_INSET %.1f mm is too deep for this spool "
                     "(groove centre would reach %.1f mm from the axis)"
                     % (face_inset, r - face_inset))
# u of the middle of each straight side: end the run there and it finishes
# pointing along the long axis, in the middle of the face, which is where a
# connector wants to lie. FACE_TURN is the minimum - the run is stretched to
# whichever of those comes next.
def face_pt(u_start, sgn, span, t):
    """point on a face run, t = 0 at the ramp, 1 at the end of the turn-in"""
    x, y, _, _ = stadium_xy(u_start + sgn * t * span)
    nx, ny = inward_dir(x, y)
    o = face_inset * smooth(min(1.0, t * span / face_trans))
    return x + nx * o, y + ny * o


def face_run_length(u_start, sgn, span):
    """length of the turned-in part"""
    if span <= 0:
        return 0.0
    total, prev, n = 0.0, None, 64
    for i in range(n + 1):
        cur = face_pt(u_start, sgn, span, i / float(n))
        if prev is not None:
            total += math.hypot(cur[0] - prev[0], cur[1] - prev[1])
        prev = cur
    return total


FACE_GEO = dict(S=S, r=r, P=P, R=R, MIN_WALL=MIN_WALL, WIDTH=WIDTH,
                LENGTH=LENGTH, inset=face_inset, turn=FACE_TURN,
                allow=CONNECTOR_ALLOWANCE, bend=FACE_BEND, d=d,
                width=CONNECTOR_WIDTH, trans=face_trans)


def pick_face_run(u_start, sgn, spans=None, collect=False):
    """see face_plan; this is the build's call into it"""
    return face_plan(FACE_GEO, u_start, sgn, spans, collect)


def spiral_from(len_bot, len_top):
    """turns and height left for the side wall once both ends have taken theirs"""
    spiral = CABLE_LENGTH - (2.0 * ramp3d + len_bot + len_top
                             + 2.0 * CONNECTOR_ALLOWANCE)
    if spiral <= P:
        raise ValueError("Cable too short for this spool size")
    pit = d + MIN_WALL
    if HEIGHT <= 0:
        return spiral, spiral / math.hypot(P, pit), pit
    for _ in range(10):                 # 3D length depends on pitch
        t = spiral / math.hypot(P, pit)
        pit = (HEIGHT - 2.0 * z0) / t
    return spiral, t, max(pit, d + MIN_WALL)


def arc_length_of(pts):
    return sum(math.hypot(pts[i + 1][0] - pts[i][0], pts[i + 1][1] - pts[i][1])
               for i in range(len(pts) - 1))


def run_length(u_start, sgn, opt):
    """3D length of a face run option: turn-in + release arc + straight"""
    return (face_run_length(u_start, sgn, opt[0]) + arc_length_of(opt[1])
            + opt[3])


FACE_GEO["ramp_u"] = RAMP_LENGTH
FACE_GEO["len_of"] = run_length
_fit = fit_runs(FACE_GEO, CABLE_LENGTH, ramp3d, CONNECTOR_ALLOWANCE, z0,
                HEIGHT, d + MIN_WALL,
                lambda u, sg: pick_face_run(u, sg, collect=True))
(turns, pitch, _bot, face_len_bot, _top, face_len_top, cable_used,
 pocket_max) = _fit
span_bot, arc_bot, tail_dir_bot, tail_len_bot = _bot[0], _bot[1], _bot[2], _bot[3]
span_top, arc_top, tail_dir_top, tail_len_top = _top[0], _top[1], _top[2], _top[3]
turn_len_bot = face_len_bot - arc_length_of(arc_bot) - tail_len_bot
turn_len_top = face_len_top - arc_length_of(arc_top) - tail_len_top
if HEIGHT > 0 and pitch < d + MIN_WALL:
    raise ValueError("HEIGHT too small: need >= %.1f mm "
                     "(or increase LENGTH/WIDTH)"
                     % (2.0 * z0 + (d + MIN_WALL) * turns))
H = HEIGHT if HEIGHT > 0 else 2.0 * z0 + pitch * turns
L_spiral = turns * math.hypot(P, pitch)
if cable_used > CABLE_LENGTH + 1.0:
    warn("this design wants %.0f mm of cable, %.0f mm more than you have"
         % (cable_used, cable_used - CABLE_LENGTH))
if FACE_TURN > 0 and pocket_max < CONNECTOR_ALLOWANCE:
    warn("a %.0f mm connector pocket does not fit on this face - the longest "
         "clear %.0f mm wide straight is %.0f mm. Shorten the pocket, narrow "
         "it, or make the spool bigger."
         % (CONNECTOR_ALLOWANCE, CONNECTOR_WIDTH, pocket_max))


u_end = turns * P                       # perimeter-parameter at spiral end
zt = H - zb                             # centre z of top face channel
z_end = z0 + pitch * turns
u_face_bot_end = -RAMP_LENGTH           # ramp start = end of the bottom face run
u_face_top_start = u_end + RAMP_LENGTH  # ramp end   = start of the top face run
u_face_bot = u_face_bot_end - span_bot     # end of the turn-in; the tail and
u_face_top = u_face_top_start + span_top   # then the anchor follow from there

# a run that laps back over itself has to step in by a groove width per lap
if FACE_TURN >= 1.0 and face_inset < FACE_TURN * (d + MIN_WALL):
    raise ValueError("the face run makes %.2f laps but only steps in %.1f mm, "
                     "so it laps back over itself - it needs >= %.1f mm "
                     "(raise FACE_INSET or lower FACE_TURN)"
                     % (FACE_TURN, face_inset, FACE_TURN * (d + MIN_WALL)))

log("perimeter/turn %.1f  turns %.2f  pitch %.2f  height %.1f"
    % (P, turns, pitch, H))


# ---------------------------------------------------------------- geometry helpers
def z_of(u):
    if u < 0:
        return z0 - (z0 - zb) * smooth(-u / RAMP_LENGTH)
    if u <= u_end:
        return z0 + pitch * u / P
    return z_end + (zt - z_end) * smooth((u - u_end) / RAMP_LENGTH)


def off_of(u):
    """how far the centre-line has moved inward from the wall; 0 everywhere
    except the two face runs, where it eases in over face_trans and then holds
    that depth; the smoothstep keeps the join with the ramp tangent-continuous"""
    if u < u_face_bot_end and span_bot > 0:
        return face_inset * smooth(min(1.0, (u_face_bot_end - u) / face_trans))
    if u > u_face_top_start and span_top > 0:
        return face_inset * smooth(min(1.0, (u - u_face_top_start) / face_trans))
    return 0.0


# --- exact centre-line -------------------------------------------------------
# The centre-line lies on the surface of the stadium prism, so it decomposes
# into exact geometry: the straight sides give 3D line segments, the round ends
# give true helix arcs.  Building the spine this way (instead of interpolating a
# BSpline through sampled points) is what makes the sweep work - OCC's
# BRepOffsetAPI_MakePipeShell fails with "MakeSolid" on a BSpline spine.
KNOTS = [0.0, S, S + math.pi * r, 3.0 * S + math.pi * r,
         3.0 * S + 2.0 * math.pi * r, P]
KINDS = ["L", "A+", "L", "A-", "L"]      # straight / +X end / straight / -X end


def segment_of(k):
    """(start, end, kind) of the stadium segment holding k in [0, P);
    zero-length segments (LENGTH == WIDTH) are skipped."""
    for i in range(5):
        if k < KNOTS[i + 1] - 1e-9:
            return KNOTS[i], KNOTS[i + 1], KINDS[i]
    return KNOTS[4], KNOTS[5], KINDS[4]


def path_point(u):
    x, y, _, _ = stadium_xy(u)
    o = off_of(u)
    if o:
        # moving toward the centre segment keeps the same inward direction, so
        # the offset curve is just the same stadium at a smaller radius
        nx, ny = inward_dir(x, y)
        x, y = x + nx * o, y + ny * o
    return V(x, y, z_of(u))


def path_edge(u1, u2):
    """one exact edge of the centre-line; u1..u2 must stay inside one segment"""
    z1, z2 = z_of(u1), z_of(u2)
    lo, _, kind = segment_of(0.5 * (u1 + u2) % P)
    if off_of(u1) > 1e-9 or off_of(u2) > 1e-9:
        # face run: the radius shrinks as we go, so this is neither a helix nor
        # a straight line. The pieces are short (cut at SAMPLE_STEP), so fit an
        # arc through three points and fall back to a chord if they are collinear.
        a, b = path_point(u1), path_point(u2)
        try:
            return Part.Arc(a, path_point(0.5 * (u1 + u2)), b).toShape()
        except Exception:
            return Part.LineSegment(a, b).toShape()
    if kind == "L":
        return Part.LineSegment(path_point(u1), path_point(u2)).toShape()
    cx = S if kind == "A+" else -S
    th0 = (-math.pi / 2 if kind == "A+" else math.pi / 2) + (u1 % P - lo) / r
    dth = (u2 - u1) / r
    dz = z2 - z1
    if abs(dz) < 1e-7:                      # flat -> plain circular arc
        p = [V(cx + r * math.cos(th0 + dth * f),
               r * math.sin(th0 + dth * f), z1) for f in (0.0, 0.5, 1.0)]
        return Part.Arc(*p).toShape()
    e = Part.makeHelix(2.0 * math.pi * dz / dth, dz, r).Edges[0]
    e.rotate(V(0, 0, 0), V(0, 0, 1), math.degrees(th0))
    e.translate(V(cx, 0, z1))
    return e


def split_u(ua, ub, step):
    """u values from ua to ub, cut at every stadium knot; with step given the
    pieces are additionally capped at that length (needed on the ramps, where
    z is not linear in u, so one piece = one constant-pitch helix)."""
    cuts = set([ua, ub])
    t = int(math.floor(ua / P))
    while t * P < ub:
        for k in KNOTS:
            if ua + 1e-7 < t * P + k < ub - 1e-7:
                cuts.add(t * P + k)
        t += 1
    cuts = sorted(cuts)
    if not step:
        return cuts
    out = []
    for a, b in zip(cuts, cuts[1:]):
        m = max(1, int(math.ceil((b - a) / step)))
        out += [a + (b - a) * j / m for j in range(m)]
    out.append(cuts[-1])
    return out


def centre_line():
    us = (split_u(u_face_bot_end, 0.0, SAMPLE_STEP)[:-1]
          + split_u(0.0, u_end, None)[:-1]
          + split_u(u_end, u_face_top_start, SAMPLE_STEP))
    edges = [path_edge(us[i], us[i + 1]) for i in range(len(us) - 1)
             if us[i + 1] - us[i] > 1e-7]
    return Part.Wire(edges)


def sweep_circle(spine):
    """circle of radius R swept along the spine, as a solid"""
    e0 = spine.OrderedEdges[0]
    prof = Part.Wire(Part.Circle(e0.valueAt(e0.FirstParameter),
                                 e0.tangentAt(e0.FirstParameter), R).toShape())
    try:
        sol = spine.makePipeShell([prof], True, False)
        if sol.isValid() and sol.Volume > 0:
            return sol
        warn("sweep result invalid, falling back to per-edge sweep")
    except Exception as e:
        warn("single sweep failed (%s), falling back to per-edge sweep" % e)
    parts = []
    for e in spine.OrderedEdges:
        p = e.valueAt(e.FirstParameter)
        pr = Part.Wire(Part.Circle(p, e.tangentAt(e.FirstParameter), R).toShape())
        parts.append(Part.Wire([e]).makePipeShell([pr], True, False))
        parts.append(Part.makeSphere(R, p))
    last = spine.OrderedEdges[-1]
    parts.append(Part.makeSphere(R, last.valueAt(last.LastParameter)))
    return parts[0].fuse(parts[1:])


def face_slot(ua, ub, zc, top, arc_pts=(), tail_dir=None, tail_len=0.0):
    """The face run, as one prismatic channel following the path.

    The swept tube stops where the ramp reaches the face; from there the groove
    is a plain straight-sided channel cut in from the face, which is what the
    cable needs anyway and what a wound cable's last turn looks like. Keeping
    the two apart matters: when the tube ran alongside the slot for the whole
    run their surfaces were tangent, and the kernel answered that with a bigger
    volume than it started with and a sealed void inside the part.

    The channel is a hair oversize (SLOT_EPS) and overlaps the end of the tube,
    so at the junction the tube is strictly inside it - a clean crossing rather
    than a tangency. It is built in overlapping chunks and fused, because as a
    single polygon the ribbon self-intersects once the run laps over itself, and
    the release arc plus the straight are built separately from the turn-in for
    the same reason: they cut back across the middle, so sharing a chunk with
    the turn-in can put a crossing inside one polygon.
    """
    hw = R + SLOT_EPS
    lo = (zc - R - SLOT_EPS) if top else -1.0
    hi = (H + 1.0) if top else (zc + R + SLOT_EPS)
    up = V(0, 0, hi - lo)

    def ribbon(flat, step=24):
        """prisms along a list of (x, y), in overlapping chunks"""
        out, n = [], len(flat)
        edge = []
        for i, (x, y) in enumerate(flat):
            px, py = flat[max(0, i - 1)]
            qx, qy = flat[min(n - 1, i + 1)]
            dx, dy = qx - px, qy - py
            m = math.hypot(dx, dy) or 1.0
            nx, ny = -dy / m, dx / m
            edge.append((V(x + nx * hw, y + ny * hw, lo),
                         V(x - nx * hw, y - ny * hw, lo)))
        for i in range(0, max(1, n - 1), step):
            seg = edge[i:min(i + step + 2, n)]
            if len(seg) < 2:
                continue
            ring = [q[1] for q in seg] + [q[0] for q in reversed(seg)]
            out.append(Part.Face(Part.makePolygon(ring + [ring[0]])).extrude(up))
        return out

    n = max(12, int(math.ceil(abs(ub - ua) / 1.5)))
    turn = []
    for i in range(n + 1):
        q = path_point(ua + (ub - ua) * i / n)
        turn.append((q.x, q.y))
    # The two ends are walked in opposite directions, so put the end the arc
    # hangs off first either way - otherwise the tail is stitched to the ramp
    # end instead and the ribbon jumps clean across the part.
    if arc_pts:
        ax, ay = arc_pts[0]
        if (math.hypot(turn[-1][0] - ax, turn[-1][1] - ay)
                < math.hypot(turn[0][0] - ax, turn[0][1] - ay)):
            turn.reverse()
    parts = ribbon(turn)

    tail = list(arc_pts)
    if tail and tail_dir is not None and tail_len > 0:
        ex, ey = tail[-1]
        tail.append((ex + tail_dir[0] * tail_len, ey + tail_dir[1] * tail_len))
    if len(tail) > 1:
        # Start a little back down the turn-in so the two overlap properly.
        # This has to happen before the resampling below, or it drags the first
        # point back past the second and flips that segment.
        if len(turn) > 1:
            dx, dy = turn[1][0] - turn[0][0], turn[1][1] - turn[0][1]
            m = math.hypot(dx, dy)
            if m > 1e-9:
                tail.insert(0, (turn[0][0] + dx / m * 2.0,
                                turn[0][1] + dy / m * 2.0))
        # Even out the spacing. The arc samples sit ~1 mm apart and the straight
        # arrives as one long jump, so the ribbon normal at the join averages
        # two quite different directions and the quad there twists.
        even = [tail[0]]
        for (x0, y0), (x1, y1) in zip(tail, tail[1:]):
            k = max(1, int(math.ceil(math.hypot(x1 - x0, y1 - y0) / 1.5)))
            even += [(x0 + (x1 - x0) * j / k, y0 + (y1 - y0) * j / k)
                     for j in range(1, k + 1)]
        parts += ribbon(even, step=8)
    return parts[0] if len(parts) == 1 else parts[0].fuse(parts[1:])


# ---------------------------------------------------------------- body
def make_body():
    hw = WIDTH / 2.0
    if S < 1e-6:
        body = Part.makeCylinder(hw, H)
    else:
        p1, p2 = V(-S, -hw, 0), V(S, -hw, 0)
        p3, p4 = V(S, hw, 0), V(-S, hw, 0)
        edges = [
            Part.LineSegment(p1, p2).toShape(),
            Part.Arc(p2, V(S + hw, 0, 0), p3).toShape(),
            Part.LineSegment(p3, p4).toShape(),
            Part.Arc(p4, V(-S - hw, 0, 0), p1).toShape(),
        ]
        body = Part.Face(Part.Wire(edges)).extrude(V(0, 0, H))
    if EDGE_FILLET > 0:
        fe = [e for e in body.Edges
              if all(abs(v.Z) < 1e-6 or abs(v.Z - H) < 1e-6 for v in e.Vertexes)
              and abs(e.Vertexes[0].Z - e.Vertexes[-1].Z) < 1e-6]
        try:
            body = body.makeFillet(EDGE_FILLET, fe)
        except Exception as e:
            warn("fillet skipped: %s" % e)
    return body


# ---------------------------------------------------------------- build
doc = App.ActiveDocument or App.newDocument("CableSpool")

spine = centre_line()
log("sweeping groove (%d edges, %.0f mm centre-line) ..."
    % (len(spine.Edges), spine.Length))
groove = sweep_circle(spine)

def anchor_at(u_run_end, arc_pts, tail_dir, tail_len, z):
    """end of the face run; with FACE_TURN = 0 there is none, so the cable just
    leaves at the ramp and that is where the pocket starts"""
    if not arc_pts:
        p = path_point(u_run_end)
        return V(p.x, p.y, z)
    x, y = arc_pts[-1]
    return V(x + tail_dir[0] * tail_len, y + tail_dir[1] * tail_len, z)


anchor_bot = anchor_at(u_face_bot, arc_bot, tail_dir_bot, tail_len_bot, 0.0)
anchor_top = anchor_at(u_face_top, arc_top, tail_dir_top, tail_len_top, H)
def from_axis(x, y):
    return math.hypot(x - max(-S, min(S, x)), y)


def pocket_reach(anchor, dirn):
    """how far from the axis the connector pocket's corners get"""
    nx, ny = -dirn[1], dirn[0]
    hw2 = CONNECTOR_WIDTH / 2.0
    return max(from_axis(anchor.x + dirn[0] * t + nx * w,
                         anchor.y + dirn[1] * t + ny * w)
               for t in (0.0, CONNECTOR_ALLOWANCE) for w in (-hw2, hw2))


if CONNECTOR_DEPTH > face_depth and FACE_TURN > 0:
    for tag, anc, dirn in (("bottom", anchor_bot, tail_dir_bot),
                           ("top", anchor_top, tail_dir_top)):
        reach = pocket_reach(anc, dirn)
        if reach > r - R:
            warn("%s connector pocket (%.0f x %.0f mm) reaches %.1f mm from "
                 "the axis but solid material only goes to %.1f - cutting it "
                 "%.0f mm deep would break into the groove in the wall. Make "
                 "the spool wider, or the pocket narrower/shorter."
                 % (tag, CONNECTOR_ALLOWANCE, CONNECTOR_WIDTH, reach, r - R,
                    CONNECTOR_DEPTH))
        else:
            log("%s pocket %.0f x %.0f mm fits over solid material with "
                "%.1f mm to spare (can be cut the full %.1f mm deep)"
                % (tag, CONNECTOR_ALLOWANCE, CONNECTOR_WIDTH,
                   (r - R) - reach, H / 2.0))

slots = []
if span_bot > 0 or span_top > 0:
    lap = min(2.0 * SAMPLE_STEP, RAMP_LENGTH * 0.5)
    slots = [face_slot(u_face_bot, u_face_bot_end + lap, zb, False,
                       arc_bot, tail_dir_bot, tail_len_bot),
             face_slot(u_face_top_start - lap, u_face_top, zt, True,
                       arc_top, tail_dir_top, tail_len_top)]

log("boolean cut ...")
# Cut sequentially (groove, then channels). Fusing all tools first, or cutting
# them in one multi-tool call, tends to yield an invalid/split result because
# the groove and channel shapes touch each other near the ramps; one cut at a
# time keeps every intermediate result a single valid solid.
# One tool at a time: fusing them all first, or passing them as one multi-tool
# cut, gives an invalid or split result where the tools touch.
spool = make_body().cut(groove)
for slot in slots:
    spool = spool.cut(slot)
try:
    # .copy() matters: removeSplitter damages the shape it is called on even
    # when its return value is thrown away, so refining in place would leave us
    # with the broken solid we are trying to reject.
    refined = spool.copy().removeSplitter()
    if refined.isValid() and len(refined.Solids) == len(spool.Solids):
        spool = refined
    else:
        warn("removeSplitter would have invalidated the shape - kept unrefined")
except Exception:
    pass
if not spool.isValid():
    warn("result shape reports invalid - try a smaller SAMPLE_STEP")

base = doc.addObject("Part::Feature", "CableSpool_Base")
base.Shape = spool

sp = doc.addObject("Part::Feature", "SpiralPath")
sp.Shape = spine
try:
    sp.ViewObject.Visibility = False
except Exception:
    pass

for name, p in (("Anchor_Bottom", anchor_bot), ("Anchor_Top", anchor_top)):
    a = doc.addObject("Part::Feature", name)
    a.Shape = Part.Vertex(p)
    try:
        a.ViewObject.PointSize = 8
        a.ViewObject.PointColor = (1.0, 0.0, 0.0)
    except Exception:
        pass

try:
    body = doc.addObject("PartDesign::Body", "CableSpool")
    body.BaseFeature = base
except Exception as e:
    warn("could not create PartDesign Body (%s); use CableSpool_Base" % e)

doc.recompute()
try:
    import FreeCADGui
    FreeCADGui.SendMsgToActiveView("ViewFit")
except Exception:
    pass

log("DONE  size %.1f x %.1f x %.1f mm" % (LENGTH, WIDTH, H))
log("groove Ø%.2f, centre radius %.2f, turns %.2f, pitch %.2f"
    % (d, r, turns, pitch))
# What you actually see on the outside. The opening is widest at
# GROOVE_DEPTH_FAC 0.5 and narrows either side of it: above, because the groove
# is undercut and curves back over; below, because it is a shallow scallop that
# never reaches full width. Either way the rib between turns then looks wider
# than MIN_WALL, which is the real minimum and sits below the surface.
open_w = 2.0 * math.sqrt(max(R * R - (depth - R) ** 2, 0.0))
log("surface opening %.2f mm, visible rib %.2f mm (true min wall %.2f mm)"
    % (open_w, pitch - open_w, MIN_WALL))
log("roof over the face channel %.2f mm (face channel ends at z %.2f, first "
    "turn starts at %.2f)" % (face_clear, face_depth, z0 - R))
if face_clear < 0.8:
    warn("only %.2f mm of material over the face channel - the spiral groove "
         "above it will very nearly break through; raise FACE_CLEAR"
         % face_clear)
if pitch - open_w > 1.6 * MIN_WALL:
    log("   -> move GROOVE_DEPTH_FAC (now %.2f) toward 0.5 for a wider "
        "opening / tighter looking coils" % GROOVE_DEPTH_FAC)
exit_deg = (math.degrees(math.atan2(abs(tail_dir_bot[1]), abs(tail_dir_bot[0])))
            if (tail_dir_bot[0] or tail_dir_bot[1]) else 0.0)
log("face run: %.2f/%.2f lap turn-in (%.0f/%.0f mm), swung out at %.0f deg, "
    "then %.0f/%.0f mm straight; tightening %.1f mm inward, tightest bend "
    "radius %.1f mm"
    % (span_bot / P, span_top / P, turn_len_bot, turn_len_top, exit_deg,
       tail_len_bot, tail_len_top, face_inset, r - face_inset))
log("   (that angle is picked to leave the longest clear %.0f mm wide corridor "
    "for the connector)" % CONNECTOR_WIDTH)
if r - face_inset < 1.5 * d:
    warn("face run ends at a %.1f mm bend radius, tight for a %.1f mm cable - "
         "raise FACE_INSET's end radius or lower FACE_INSET"
         % (r - face_inset, CABLE_DIAMETER))
log("cable: spiral %.0f + 2 x %.0f (ramp+face run+pocket) = %.1f mm of your "
    "%.0f mm, %.1f mm spare"
    % (turns * math.hypot(P, pitch), ramp3d + 0.5 * (face_len_bot + face_len_top)
       + CONNECTOR_ALLOWANCE, cable_used, CABLE_LENGTH,
       abs(CABLE_LENGTH - cable_used) if abs(CABLE_LENGTH - cable_used) > 0.05
       else 0.0))
log("pocket anchors: bottom (%.1f, %.1f, 0)  top (%.1f, %.1f, %.1f)"
    % (anchor_bot.x, anchor_bot.y, anchor_top.x, anchor_top.y, H))
log("-> sketch your connector pocket on each face from the anchor; the "
    "channel stops %.0f mm short of the far side to leave room for it "
    "(lower CONNECTOR_ALLOWANCE and the channel runs further)"
    % CONNECTOR_ALLOWANCE)
