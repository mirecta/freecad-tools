# =============================================================================
#  CookieCutter.FCMacro  v1
#  –  Cookie cutter mesh from any planar curve
# =============================================================================
#
#  WORKFLOW
#  --------
#  1. Select the curve: a sketch, any Draft object (line, wire, arc, B-spline…),
#     a face, or single edges of any of them.  Several curves are fine — a ring
#     cuts a donut, and open lines may be mixed in with closed ones.
#  2. Run the macro and set the profile in the dialog — the inputs sit right
#     on the drawing of the profile, each on the dimension it sets:
#
#              B                    A  total height
#        ┌───────────┐              B  flange width (measured from the curve)
#        │      ┌────┘ C            C  flange thickness
#        │      │                   D  straight part of the wall under the flange
#      A │      │ D                 E  width of the cutting edge
#        │  F  ╱                    F  wall width where the taper starts
#        │    ╱
#        └───┘
#          E
#
#     The straight side A sits on the curve, so the cookie comes out exactly
#     the shape that was drawn.  The profile is printed flange-down: the flange
#     lies in the plane of the curve, the cutting edge points along its normal.
#
#     An open line has no inside to keep clear, so its wall is centred on the
#     line: E, F and B are then the full widths, half to each side.
#  3. Click [Generate].  The dialog stays open — change a value and generate
#     again, the previous result is replaced.
#
#  SEVERAL CURVES
#  --------------
#  Curves must not cross.  A curve inside another one is an inner knife:
#
#    cutting (default)  it cuts a hole.  Its profile comes out mirrored, the
#                       straight side still facing the cookie and the wall
#                       standing in the scrap.
#    imprint only       it presses a line into the dough instead: a blunt wall
#                       of the full width F, centred on the curve and shorter
#                       than the cutting knives by a set amount.
#
#  Open lines are always walls centred on the line.
#
#  The knives are tied together on the flange side, either by bridges — flat
#  bars as thick as the flange, laid across the cookie where the knives come
#  closest, a set number to each knife and spread round it — or by a full
#  plate over the whole cookie.  Joined that way, the
#  centred walls have no flange of their own; the bridges or the plate carry
#  them.
#
#  TIGHT CURVES
#  ------------
#  Sweeping the profile along the curve folds over itself wherever the curve
#  bends tighter than the profile is wide.  So nothing is swept: the cutter is
#  built from true offsets of the curve.  Every profile corner sits at some
#  distance d from the curve, the offset at that d is one contour of the mesh,
#  and the faces are stretched between neighbouring contours.  The offsets come
#  from Clipper (Path.Area), which drops the folded parts, so pockets narrower
#  than the flange simply fill up and the mesh stays a closed solid.
#
#  The taper is the one face that is neither flat nor vertical: its height
#  follows the distance from the curve.  Where two offset fronts run into each
#  other that distance has a crease (the bottom of a V between two walls), and
#  no contour runs along it.  So the taper is refined after triangulation: any
#  edge or facet that strays from the true distance by more than the accuracy
#  is split, with the new point placed at its true height, until the creases
#  are followed as closely as the curve itself.
#
# =============================================================================

import FreeCAD
import Part
import Mesh
import math

V = FreeCAD.Vector

EPS  = 1e-7
GRID = 6        # decimals every contour point is snapped to
CLOSE_TOL = 1e-3  # ends of an offset loop this close count as meeting
PREF = "User parameter:BaseApp/Preferences/Macros/CookieCutter"


class CutterError(Exception):
    pass


# ── polygons ──────────────────────────────────────────────────────────────────

def loop_area(lp):
    a = 0.0
    for i in range(len(lp)):
        x1, y1 = lp[i - 1]
        x2, y2 = lp[i]
        a += x1 * y2 - x2 * y1
    return 0.5 * a


def point_in_loop(p, lp):
    x, y = p
    inside = False
    for i in range(len(lp)):
        x1, y1 = lp[i - 1]
        x2, y2 = lp[i]
        if (y1 > y) != (y2 > y) and x < x1 + (y - y1) * (x2 - x1) / (y2 - y1):
            inside = not inside
    return inside


def clean_path(pts, min_seg=1e-3):
    """Snap to the grid and drop the points that fall together"""
    out = []
    for x, y in pts:
        p = (round(x, GRID), round(y, GRID))
        if not out or math.hypot(p[0] - out[-1][0], p[1] - out[-1][1]) > min_seg:
            out.append(p)
    return out if len(out) > 1 else None


def clean_loop(pts, min_seg=1e-3):
    out = clean_path(pts, min_seg) or []
    while len(out) > 1 and math.hypot(out[0][0] - out[-1][0],
                                      out[0][1] - out[-1][1]) <= min_seg:
        out.pop()
    if len(out) < 3 or abs(loop_area(out)) < 1e-8:
        return None
    return out


def orient_loops(loops):
    """Turn every loop so that the region it bounds lies on its left"""
    out = []
    for i, lp in enumerate(loops):
        depth = sum(1 for j, other in enumerate(loops)
                    if j != i and point_in_loop(lp[0], other))
        ccw = loop_area(lp) > 0
        out.append(lp if ccw == (depth % 2 == 0) else lp[::-1])
    return out


def wire_points(wire, defl):
    """Wire -> list of Vectors, corners kept, curves within defl"""
    chunks = []
    for e in wire.OrderedEdges:
        pts = e.discretize(Deflection=defl)
        if len(pts) < 2:
            pts = [e.valueAt(e.FirstParameter), e.valueAt(e.LastParameter)]
        chunks.append(pts)
    if len(chunks) > 1:
        a, b = chunks[0], chunks[1]
        if min(a[0].distanceToPoint(b[0]), a[0].distanceToPoint(b[-1])) < \
           min(a[-1].distanceToPoint(b[0]), a[-1].distanceToPoint(b[-1])):
            chunks[0] = a[::-1]
    out = list(chunks[0])
    for pts in chunks[1:]:
        if out[-1].distanceToPoint(pts[-1]) < out[-1].distanceToPoint(pts[0]):
            pts = pts[::-1]
        out.extend(pts[1:])
    return out


def polygon_wire(lp):
    return Part.makePolygon([V(x, y, 0) for x, y in lp] + [V(lp[0][0], lp[0][1], 0)])


def region_faces(loops):
    """Even-odd region of the loops as planar faces (holes and islands sorted out)"""
    shape = Part.makeFace([polygon_wire(lp) for lp in loops],
                          "Part::FaceMakerBullseye")
    return shape.Faces


class SegmentGrid:
    """Distance from a point to the curve, for points no further than `reach`"""

    def __init__(self, loops, closed, reach):
        self.cell = reach
        self.segs = []
        self.cells = {}
        for lp in loops:
            for i in range(0 if closed else 1, len(lp)):
                (x1, y1), (x2, y2) = lp[i - 1], lp[i]
                k = len(self.segs)
                self.segs.append((x1, y1, x2 - x1, y2 - y1,
                                  (x2 - x1) ** 2 + (y2 - y1) ** 2))
                for cx in range(self._cell(min(x1, x2)), self._cell(max(x1, x2)) + 1):
                    for cy in range(self._cell(min(y1, y2)), self._cell(max(y1, y2)) + 1):
                        self.cells.setdefault((cx, cy), []).append(k)

    def _cell(self, v):
        return int(math.floor(v / self.cell))

    def distance(self, x, y):
        cx, cy = self._cell(x), self._cell(y)
        best = None
        seen = set()
        for ix in (cx - 1, cx, cx + 1):
            for iy in (cy - 1, cy, cy + 1):
                for k in self.cells.get((ix, iy), ()):
                    if k in seen:
                        continue
                    seen.add(k)
                    x1, y1, dx, dy, ll = self.segs[k]
                    t = ((x - x1) * dx + (y - y1) * dy) / ll
                    t = 0.0 if t < 0.0 else 1.0 if t > 1.0 else t
                    d2 = (x - x1 - t * dx) ** 2 + (y - y1 - t * dy) ** 2
                    if best is None or d2 < best:
                        best = d2
        return None if best is None else math.sqrt(best)


# ── offset engines ────────────────────────────────────────────────────────────

class AreaEngine:
    """Clipper through Path.Area — ships with every FreeCAD that has CAM"""
    name = "Path.Area (Clipper)"

    def __init__(self, loops, defl, is_open=False):
        import Path
        self._Path = Path
        self.defl = defl
        self.is_open = is_open
        self.plane = Part.makeCircle(1.0)
        if is_open:
            self.shape = Part.Compound(
                [Part.makePolygon([V(x, y, 0) for x, y in lp]) for lp in loops])
        else:
            self.shape = Part.Compound(region_faces(loops))

    def offset(self, d):
        if self.is_open and abs(d) < EPS:
            return []
        area = self._Path.Area()
        area.setParams(Coplanar=0, Fill=0, FitArcs=False, JoinType=0,
                       Accuracy=self.defl, Deflection=self.defl)
        area.setPlane(self.plane)   # a straight line would not span one
        area.add(self.shape)
        if abs(d) < EPS:
            res = area.getShape()
        else:
            res = area.makeOffset(index=-1, offset=d)
        if res is None or res.isNull():
            return []
        # Offsets come back arc-fitted whatever FitArcs says, and the fitting
        # can leave the loop a hair short of closing — so go by the end points
        # rather than by isClosed()
        loops = []
        for chain in Part.sortEdges(res.Edges):
            pts = wire_points(Part.Wire(chain), self.defl)
            if pts[0].distanceToPoint(pts[-1]) > CLOSE_TOL:
                # better no mesh than one with a contour missing
                raise CutterError(
                    "The offset at {:.3f} mm came back open.".format(abs(d)))
            loops.append([(p.x, p.y) for p in pts])
        return loops


class ShapelyEngine:
    """GEOS buffer, for builds without the CAM workbench"""
    name = "Shapely (GEOS)"

    def __init__(self, loops, defl, is_open=False):
        from shapely.geometry import Polygon, MultiLineString
        self.defl = defl
        self.is_open = is_open
        if is_open:
            self.region = MultiLineString(loops)
            return
        region = None
        for lp in loops:            # even-odd, same as the faces above
            poly = Polygon(lp).buffer(0)
            region = poly if region is None else region.symmetric_difference(poly)
        self.region = region

    def offset(self, d):
        if self.is_open and abs(d) < EPS:
            return []
        if abs(d) < EPS:
            res = self.region
        else:
            step = 2.0 * math.acos(max(0.0, 1.0 - self.defl / abs(d)))
            segs = max(4, int(math.ceil(0.5 * math.pi / step)))
            # GEOS rounds every vertex of the curve, far finer than asked for
            res = self.region.buffer(d, segs).simplify(0.5 * self.defl)
        polys = getattr(res, "geoms", [res])
        out = []
        for poly in polys:
            if poly.is_empty or poly.geom_type != "Polygon":
                continue
            out.append(list(poly.exterior.coords)[:-1])
            out.extend(list(r.coords)[:-1] for r in poly.interiors)
        return out


def make_engine(loops, defl, is_open=False, prefer=None):
    defl *= 0.25        # the curve was already cut within half the accuracy
    errors = []
    for cls in (AreaEngine, ShapelyEngine):
        if prefer and cls.__name__ != prefer:
            continue
        try:
            return cls(loops, defl, is_open)
        except ImportError as e:
            errors.append("{}: {}".format(cls.name, e))
    raise CutterError("No 2-D offset engine available.\n" + "\n".join(errors))


# ── cutter ────────────────────────────────────────────────────────────────────

def profile_points(A, B, C, D, E, F):
    """Profile outline as (distance from the curve, height), flange down,
    walked counter-clockwise from the foot of the straight side"""
    if not (A > EPS and F > EPS):
        raise CutterError("Height A and wall width F must be greater than zero.")
    if min(B, C, D, E) < 0:
        raise CutterError("Dimensions cannot be negative.")
    if E > F + EPS:
        raise CutterError("Cutting edge E cannot be wider than the wall F.")
    if C + D > A + EPS:
        raise CutterError("C + D cannot be more than the total height A.")
    if C > EPS and B > F + EPS:
        pts = [(0.0, 0.0), (B, 0.0), (B, C), (F, C), (F, C + D), (E, A), (0.0, A)]
    else:
        pts = [(0.0, 0.0), (F, 0.0), (F, C + D), (E, A), (0.0, A)]
    out = []
    for p in pts:
        if not out or abs(p[0] - out[-1][0]) > EPS or abs(p[1] - out[-1][1]) > EPS:
            out.append(p)
    return out


class MeshPool:
    """Points and facets of the whole cutter.  Every part writes into the same
    pool, so parts that meet share their points and the mesh closes up."""

    def __init__(self):
        self.points = []
        self.facets = []
        self._index = {}

    def vertex(self, x, y, z):
        key = (x, y, round(z, GRID))
        i = self._index.get(key)
        if i is None:
            i = self._index[key] = len(self.points)
            self.points.append(V(x, y, z))
        return i

    def quad(self, p, q, z0, z1):
        """Vertical face over the edge p -> q; with z0 < z1 it faces right"""
        a = self.vertex(p[0], p[1], z0)
        b = self.vertex(q[0], q[1], z0)
        c = self.vertex(q[0], q[1], z1)
        e = self.vertex(p[0], p[1], z1)
        self.facets.append((a, b, c))
        self.facets.append((a, c, e))

    def flat(self, loops, z, up):
        """Level face over the even-odd region of the loops"""
        if not loops:
            return
        known = set(p for lp in loops for p in lp)
        for face in region_faces(loops):
            fpts, ftris = face.tessellate(1.0)
            ids = []
            for p in fpts:
                xy = (round(p.x, GRID), round(p.y, GRID))
                if xy not in known:
                    raise CutterError(
                        "Triangulation added a point off the contours "
                        "({:.4f}, {:.4f}).".format(p.x, p.y))
                ids.append(self.vertex(xy[0], xy[1], z))
            for a, b, c in ftris:
                pa, pb, pc = fpts[a], fpts[b], fpts[c]
                ccw = ((pb.x - pa.x) * (pc.y - pa.y)
                       - (pb.y - pa.y) * (pc.x - pa.x)) > 0
                self.facets.append((ids[a], ids[b], ids[c]) if ccw == up else
                                   (ids[a], ids[c], ids[b]))

    def mesh(self):
        if not self.facets:
            raise CutterError("Nothing to build — the offsets came out empty.")
        return Mesh.Mesh((self.points, self.facets))


class CutterBuilder:

    def __init__(self, loops, inside=False, defl=0.02, steps=6, engine=None,
                 is_open=False, pool=None):
        clean = clean_path if is_open else clean_loop
        loops = [lp for lp in (clean(l) for l in loops) if lp]
        if not loops:
            raise CutterError("The line is too short." if is_open else
                              "The curve encloses no area.")
        self.inside = inside and not is_open
        self.is_open = is_open
        self.curve = loops
        self.defl = defl
        self.steps = max(1, int(steps))
        self.engine = make_engine(loops, defl, is_open, engine)
        self._levels = {}
        self._grid = None
        self.pool = pool or MeshPool()
        self.facets = self.pool.facets
        self._vertex = self.pool.vertex
        self.covered = {}       # level -> contour edges a bridge is joined to
        self.floor = 0.0        # ...and the height the bridges reach up to

    def contour(self, d):
        """Boundary of everything within d of the cookie (of the line, when
        it is open), solid side on the left.  None stands for no contour."""
        if d is None:
            return []
        key = round(d, 7)
        if key not in self._levels:
            raw = self.engine.offset(-key if self.inside else key)
            loops = orient_loops([lp for lp in (clean_loop(l) for l in raw) if lp])
            if self.inside:
                loops = [lp[::-1] for lp in loops]
            self._levels[key] = loops
        return self._levels[key]

    def wall(self, d, z0, z1):
        """Vertical face on contour d; faces away from the solid when z0 < z1.
        Where a bridge is joined on, the wall starts above the bridge."""
        covered = self.covered.get(round(d, 7), ())
        lo, hi = min(z0, z1), max(z0, z1)
        split = bool(covered) and lo + EPS < self.floor < hi - EPS
        for lp in self.contour(d):
            for i in range(len(lp)):
                p, q = lp[i - 1], lp[i]
                if (p, q) in covered:
                    if hi <= self.floor + EPS:
                        continue
                    a, b = (self.floor, z1) if z0 < z1 else (z0, self.floor)
                    self.pool.quad(p, q, a, b)
                elif split:
                    # same points along the top of the bridges as on them
                    self.pool.quad(p, q, z0, self.floor)
                    self.pool.quad(p, q, self.floor, z1)
                else:
                    self.pool.quad(p, q, z0, z1)

    def band(self, d0, z0, d1, z1, up):
        """Face between contours d0 and d1, each at its own height"""
        level = {}
        for d in (d0, d1):
            for lp in self.contour(d):
                for p in lp:
                    level[p] = d
        loops = self.contour(d0) + self.contour(d1)
        if not loops:
            return
        pts, index, tris = [], {}, []       # (x, y, distance), all facets ccw
        for face in region_faces(loops):
            fpts, ftris = face.tessellate(1.0)
            ids = []
            for p in fpts:
                xy = (round(p.x, GRID), round(p.y, GRID))
                if xy not in level:
                    raise CutterError(
                        "Triangulation added a point off the contours "
                        "({:.4f}, {:.4f}).".format(p.x, p.y))
                i = index.get(xy)
                if i is None:
                    i = index[xy] = len(pts)
                    pts.append((xy[0], xy[1], level[xy]))
                ids.append(i)
            for a, b, c in ftris:
                pa, pb, pc = fpts[a], fpts[b], fpts[c]
                ccw = ((pb.x - pa.x) * (pc.y - pa.y)
                       - (pb.y - pa.y) * (pc.x - pa.x)) > 0
                tris.append((ids[a], ids[b], ids[c]) if ccw else
                            (ids[a], ids[c], ids[b]))
        if abs(z0 - z1) > EPS:
            tris = self._follow_distance(pts, index, tris, min(d0, d1), max(d0, d1))
        if abs(z0 - z1) > EPS:
            slope = (z1 - z0) / (d1 - d0)
            ids = [self._vertex(x, y, z0 + (d - d0) * slope) for x, y, d in pts]
        else:
            ids = [self._vertex(x, y, z0) for x, y, _d in pts]
        for a, b, c in tris:
            if up:
                self.facets.append((ids[a], ids[b], ids[c]))
            else:
                self.facets.append((ids[a], ids[c], ids[b]))

    def _follow_distance(self, pts, index, tris, lo, hi):
        """Split the edges and facets of a sloped band that cut across a
        crease of the distance field, until none is off by more than the
        accuracy.  Contour edges are shared with the neighbours and stay."""
        if self._grid is None or self._grid.cell < hi:
            self._grid = SegmentGrid(self.curve, not self.is_open,
                                     max(hi * 1.05, 10.0 * self.defl))
        grid, tol = self._grid, self.defl
        min_len = 2.0 * tol

        def dist(x, y):
            d = grid.distance(x, y)
            return hi if d is None or d > hi else lo if d < lo else d

        near = {}       # points by cell, to keep new ones from crowding
        crowd = 0.5 * tol

        def cell_of(x, y):
            return (int(math.floor(x / crowd)), int(math.floor(y / crowd)))

        for i, (x, y, _d) in enumerate(pts):
            near.setdefault(cell_of(x, y), []).append(i)

        def add(x, y, d):
            """New point, or None where one already sits: creases met from
            several edges would otherwise pile up slivers"""
            x, y = round(x, GRID), round(y, GRID)
            cx, cy = cell_of(x, y)
            for ix in (cx - 1, cx, cx + 1):
                for iy in (cy - 1, cy, cy + 1):
                    for i in near.get((ix, iy), ()):
                        if math.hypot(pts[i][0] - x, pts[i][1] - y) < crowd:
                            return None
            index[(x, y)] = len(pts)
            near.setdefault((cx, cy), []).append(len(pts))
            pts.append((x, y, d))
            return len(pts) - 1

        good_edges, good_tris = set(), set()
        for _ in range(100):
            edges = {}
            for t, (a, b, c) in enumerate(tris):
                for u, v in ((a, b), (b, c), (c, a)):
                    edges.setdefault((u, v) if u < v else (v, u), []).append(t)
            busy, cuts, flips = set(), {}, {}
            for key, ts in edges.items():
                if len(ts) != 2 or key in good_edges:
                    continue
                if ts[0] in busy or ts[1] in busy:
                    continue
                (ux, uy, ud), (vx, vy, vd) = pts[key[0]], pts[key[1]]

                def off(f):
                    """How far the edge is from the true distance at f"""
                    return abs(dist(ux + (vx - ux) * f, uy + (vy - uy) * f)
                               - (ud + (vd - ud) * f))

                worst, at = tol, None
                if math.hypot(vx - ux, vy - uy) > min_len:
                    for f in (0.5, 0.25, 0.75):
                        e = off(f)
                        if e > worst:
                            worst, at = e, f
                if at is None:
                    good_edges.add(key)
                    continue
                # An edge across a crease is often just the wrong diagonal:
                # the other one of its quad may run along the crease instead
                w0, w1 = (next(i for i in tris[t] if i not in key) for t in ts)
                (px, py, pd), (qx, qy, qd) = pts[w0], pts[w1]
                su = (qx - px) * (uy - py) - (qy - py) * (ux - px)
                sv = (qx - px) * (vy - py) - (qy - py) * (vx - px)
                if su * sv < 0 and min(abs(su), abs(sv)) > min_len * min_len:
                    alt = max(abs(dist(px + (qx - px) * f, py + (qy - py) * f)
                                  - (pd + (qd - pd) * f)) for f in (0.5, 0.25, 0.75))
                    if alt < 0.5 * worst:
                        busy.update(ts)
                        for t in ts:
                            flips[t] = (key, w0, w1)
                        continue
                # the edge crosses a crease, and is furthest off right on it:
                # close in on that point so the new vertex lands on the crease
                f0, f1 = at - 0.25, at + 0.25
                for _i in range(30):
                    fa, fb = f0 + (f1 - f0) / 3.0, f1 - (f1 - f0) / 3.0
                    if off(fa) < off(fb):
                        f0 = fa
                    else:
                        f1 = fb
                at = min(max(0.5 * (f0 + f1), 0.05), 0.95)
                x, y = ux + (vx - ux) * at, uy + (vy - uy) * at
                m = add(x, y, dist(x, y))
                if m is None:
                    good_edges.add(key)
                    continue
                busy.update(ts)
                for t in ts:
                    cuts[t] = (key, m)
            for t, tri in enumerate(tris):
                if t in busy or tri in good_tris:
                    continue
                (ax, ay, ad), (bx, by, bd), (cx, cy, cd) = (pts[i] for i in tri)
                area2 = abs((bx - ax) * (cy - ay) - (by - ay) * (cx - ax))
                x, y = (ax + bx + cx) / 3.0, (ay + by + cy) / 3.0
                d = dist(x, y) if area2 > min_len * min_len else None
                if d is None or abs(d - (ad + bd + cd) / 3.0) <= tol:
                    good_tris.add(tri)
                    continue
                m = add(x, y, d)
                if m is None:
                    good_tris.add(tri)
                    continue
                cuts[t] = (None, m)
            if not cuts and not flips:
                break
            out = []
            for t, (a, b, c) in enumerate(tris):
                if t in flips:
                    key, w0, w1 = flips[t]
                    while a in key:         # start at the corner off the edge
                        a, b, c = b, c, a
                    # keeps (corner, next, far corner): ccw, one from each side
                    out.append((a, b, w1 if a == w0 else w0))
                    continue
                if t not in cuts:
                    out.append((a, b, c))
                    continue
                key, m = cuts[t]
                if key is None:
                    out.extend(((a, b, m), (b, c, m), (c, a, m)))
                    continue
                while not (a in key and b in key):      # bring the cut edge first
                    a, b, c = b, c, a
                out.extend(((a, m, c), (m, b, c)))
            tris = out
        return tris

    def build(self, chain, closed=True):
        """Walk the profile outline, given as (distance, height) corners
        counter-clockwise, and put a face on each of its sides"""
        chain = [p for i, p in enumerate(chain) if i == 0 or p != chain[i - 1]]
        n = len(chain)
        for i in range(n if closed else n - 1):
            (da, za), (db, zb) = chain[i], chain[(i + 1) % n]
            if da is not None and db is not None and abs(da - db) < EPS:
                self.wall(da, za, zb)
                continue
            up = da is not None and (db is None or db < da)
            if abs(za - zb) < EPS:
                self.band(da, za, db, zb, up)
                continue
            for j in range(self.steps):
                t0, t1 = j / float(self.steps), (j + 1) / float(self.steps)
                self.band(da + (db - da) * t0, za + (zb - za) * t0,
                          da + (db - da) * t1, za + (zb - za) * t1, up)


# ── bridges ───────────────────────────────────────────────────────────────────

def _cross(o, a, b):
    return (a[0] - o[0]) * (b[1] - o[1]) - (a[1] - o[1]) * (b[0] - o[0])


def _segments_cross(p1, p2, p3, p4):
    d1, d2 = _cross(p3, p4, p1), _cross(p3, p4, p2)
    d3, d4 = _cross(p1, p2, p3), _cross(p1, p2, p4)
    return ((d1 > 0) != (d2 > 0)) and ((d3 > 0) != (d4 > 0))


class Rim:
    """One loop the bridges may be joined to: an edge of the cookie, or the
    foot of an inner wall.  Runs with the open cookie area on its left."""

    def __init__(self, builder, level, index, flip):
        self.builder, self.key, self.index, self.flip = \
            builder, round(level, 7), index, flip
        lp = builder.contour(level)[index]
        self.loop = lp[::-1] if flip else list(lp)
        self.cum = [0.0]
        for i in range(len(self.loop)):
            (x1, y1), (x2, y2) = self.loop[i], self.loop[(i + 1) % len(self.loop)]
            self.cum.append(self.cum[-1] + math.hypot(x2 - x1, y2 - y1))
        self.length = self.cum[-1]
        self.cuts = []          # arc positions where bridge sides land
        self.taken = []         # (start, end) arcs already under a bridge

    def at(self, s):
        s %= self.length
        lo, hi = 0, len(self.loop)
        while hi - lo > 1:
            mid = (lo + hi) // 2
            if self.cum[mid] <= s:
                lo = mid
            else:
                hi = mid
        (x1, y1), (x2, y2) = self.loop[lo], self.loop[(lo + 1) % len(self.loop)]
        f = (s - self.cum[lo]) / max(self.cum[lo + 1] - self.cum[lo], 1e-12)
        return (x1 + (x2 - x1) * f, y1 + (y2 - y1) * f)

    def free(self, s0, s1):
        """Is the arc s0..s1 clear of the bridges already here?"""
        for t0, t1 in self.taken:
            for shift in (-self.length, 0.0, self.length):
                if s0 + shift < t1 and t0 < s1 + shift:
                    return False
        return True

    def insert_cuts(self):
        """Add the landing points to the loop; returns position -> index"""
        out, where = [], {}
        n = len(self.loop)
        for k in range(n):
            out.append(self.loop[k])
            base = len(out) - 1
            (x1, y1), (x2, y2) = self.loop[k], self.loop[(k + 1) % n]
            seg = self.cum[k + 1] - self.cum[k]
            for s in sorted(c % self.length for c in set(self.cuts)):
                if not (self.cum[k] <= s < self.cum[k + 1]):
                    continue
                if s - self.cum[k] < 1e-3:
                    where[s] = base
                elif self.cum[k + 1] - s < 1e-3:
                    where[s] = -(k + 1)     # the next original point
                else:
                    f = (s - self.cum[k]) / seg
                    pt = (round(x1 + (x2 - x1) * f, GRID),
                          round(y1 + (y2 - y1) * f, GRID))
                    if pt != out[-1]:
                        out.append(pt)
                    where[s] = len(out) - 1
        starts = {}
        j = 0
        for k in range(n):                  # where the original points ended up
            while out[j] != self.loop[k]:
                j += 1
            starts[k] = j
            j += 1
        for s, i in list(where.items()):
            if i < 0:
                where[s] = starts[(-i) % n]
        self.loop = out
        stored = out[::-1] if self.flip else out
        self.builder._levels[self.key][self.index] = stored
        return where

    def arc(self, i0, i1):
        pts = [self.loop[i0]]
        i = i0
        while i != i1:
            i = (i + 1) % len(self.loop)
            pts.append(self.loop[i])
        return pts


def _nearest(p, rim, around=None, reach=0):
    """Point of the rim nearest to p: (distance squared, its index)"""
    n = len(rim.loop)
    step = max(1, n // 150)
    span = range(0, n, step) if around is None else \
        range(around - reach, around + reach + 1)
    best = (1e300, 0)
    for j in span:
        q = rim.loop[j % n]
        d = (p[0] - q[0]) ** 2 + (p[1] - q[1]) ** 2
        if d < best[0]:
            best = (d, j % n)
    if around is None and step > 1:
        return _nearest(p, rim, best[1], step)
    return best


def _crossings(a, b):
    """Places to bridge two rims, nearest first: (distance, position on a,
    position on b).  The closest pair of points, and for a choice a dozen more
    spread round each rim — the closest spot is not always one a bar fits on,
    the round end of a thin wall for one."""
    found = []
    for src, dst, swap in ((a, b, False), (b, a, True)):
        n = len(src.loop)
        for i in range(0, n, max(1, n // 12)):
            d, j = _nearest(src.loop[i], dst)
            d2, i2 = _nearest(dst.loop[j], src)     # slide to the foot of it
            if d2 < d:
                d, i = d2, i2
            pair = (src.cum[i], dst.cum[j])
            found.append((math.sqrt(d),) + (pair[::-1] if swap else pair))
    found.sort()
    return found


def add_bridges(pool, rims, width, thickness, count=3):
    """Join the rims into one piece with flat bars across the cookie area, the
    shortest ones that fit, `count` to a knife.  Returns their number."""
    every = [seg for r in rims for seg in zip(r.loop, r.loop[1:] + r.loop[:1])]

    def in_cookie(p):
        return sum(1 for r in rims if point_in_loop(p, r.loop)) % 2 == 1

    def clear(p, q, sides):
        """Does the bar side p -> q stay within the cookie area?"""
        a = (p[0] + (q[0] - p[0]) * 1e-4, p[1] + (q[1] - p[1]) * 1e-4)
        b = (q[0] + (p[0] - q[0]) * 1e-4, q[1] + (p[1] - q[1]) * 1e-4)
        if not in_cookie((0.5 * (p[0] + q[0]), 0.5 * (p[1] + q[1]))):
            return False
        return not any(_segments_cross(a, b, c, d) for c, d in every + sides)

    links = []
    for i in range(len(rims)):
        for j in range(i + 1, len(rims)):
            spots = _crossings(rims[i], rims[j])
            links.append((spots[0][0], i, j, spots))
    links.sort()
    group = list(range(len(rims)))

    def find(i):
        while group[i] != i:
            i = group[i]
        return i

    bars, sides = [], []
    def fit(a, b, spots, narrowest=0.25):
        """The widest bar that fits, on the nearest spot it fits on"""
        full = min(width, a.length / 3.0, b.length / 3.0)
        for w in (full, 0.5 * full, 0.25 * full):
            if w < narrowest * full:
                break
            for dist, sa, sb in spots:
                if dist > 3.0 * spots[0][0] + width:
                    break
                a0, a1, b0, b1 = sa - 0.5 * w, sa + 0.5 * w, sb - 0.5 * w, sb + 0.5 * w
                pa0, pa1, pb0, pb1 = a.at(a0), a.at(a1), b.at(b0), b.at(b1)
                if (a.free(a0, a1) and b.free(b0, b1)
                        and not _segments_cross(pa0, pb1, pb0, pa1)
                        and clear(pa0, pb1, sides) and clear(pb0, pa1, sides)):
                    return a0, a1, b0, b1, pa0, pa1, pb0, pb1
        return None

    def lay(a, b, bar):
        a0, a1, b0, b1, pa0, pa1, pb0, pb1 = bar
        a.taken.append((a0, a1))
        b.taken.append((b0, b1))
        a.cuts.extend((a0, a1))
        b.cuts.extend((b0, b1))
        sides.extend(((pa0, pb1), (pb0, pa1)))
        bars.append((a, a0, a1, b, b0, b1))

    # first the fewest that make it one piece, shortest first...
    for _dist, i, j, spots in links:
        if find(i) == find(j):
            continue
        bar = fit(rims[i], rims[j], spots)
        if bar is not None:
            lay(rims[i], rims[j], bar)
            group[find(i)] = find(j)

    # ...then more, until every knife is held in `count` places: on one bar
    # alone it would swing.  Small knives first.  The knife is divided into
    # `count` sectors from the bar it has, and each sector without one is
    # searched from its middle outwards, for a full-width bar to whichever
    # knife lies nearest there, and failing that for a narrower one.
    def spread(rim, s):
        """Distance along the rim from s to the nearest bar already on it"""
        gaps = [abs((s - 0.5 * (t0 + t1) + 0.5 * rim.length) % rim.length
                    - 0.5 * rim.length) for t0, t1 in rim.taken]
        return min(gaps) if gaps else rim.length

    def bar_near(i, target, sector):
        rim = rims[i]
        tries = []
        for k in range(9):
            s = target + 0.5 * sector * ((k + 1) // 2) / 4.5 * (-1 if k % 2 else 1)
            p = rim.at(s)
            others = []
            for j, other in enumerate(rims):
                if j != i:
                    d, at = _nearest(p, other)
                    others.append((math.sqrt(d), j, other.cum[at]))
            others.sort()
            tries.append((s, others[:3]))
        for narrowest in (1.0, 0.5, 0.25):
            for s, others in tries:
                for d, j, sj in others:
                    bar = fit(rim, rims[j], [(d, s, sj)], narrowest)
                    if bar is not None:
                        lay(rim, rims[j], bar)
                        return True
        return False

    for i in sorted(range(len(rims)), key=lambda k: rims[k].length):
        rim = rims[i]
        sector = rim.length / float(count)
        anchor = 0.5 * sum(rim.taken[0]) if rim.taken else 0.0
        for k in range(0 if not rim.taken else 1, count):
            if len(rim.taken) >= count:
                break
            target = anchor + k * sector
            if spread(rim, target) > 0.5 * sector:
                bar_near(i, target, sector)

    where = dict((id(r), r.insert_cuts()) for r in rims if r.cuts)
    made = 0
    for a, a0, a1, b, b0, b1 in bars:
        wa, wb = where[id(a)], where[id(b)]
        arc_a = a.arc(wa[a0 % a.length], wa[a1 % a.length])
        arc_b = b.arc(wb[b0 % b.length], wb[b1 % b.length])
        bar = arc_a + arc_b
        if len(arc_a) < 2 or len(arc_b) < 2 or len(set(bar)) != len(bar) \
                or loop_area(bar) <= 1e-6:
            continue
        for rim, arc in ((a, arc_a), (b, arc_b)):
            edges = rim.builder.covered.setdefault(rim.key, set())
            for p, q in zip(arc, arc[1:]):
                edges.add((p, q))
                edges.add((q, p))
            rim.builder.floor = thickness
        pool.flat([bar], 0.0, up=False)
        pool.flat([bar], thickness, up=True)
        pool.quad(arc_a[-1], arc_b[0], 0.0, thickness)
        pool.quad(arc_b[-1], arc_a[0], 0.0, thickness)
        made += 1
    return made


# ── the whole cutter ──────────────────────────────────────────────────────────

JOIN_NONE, JOIN_BRIDGES, JOIN_PLATE = 0, 1, 2


def split_inner(loops):
    """Loops that lie inside another one, and the rest"""
    outer, inner = [], []
    for i, lp in enumerate(loops):
        depth = sum(1 for j, other in enumerate(loops)
                    if j != i and point_in_loop(lp[0], other))
        (inner if depth else outer).append(lp)
    return outer, inner


def build_cutter(loops, A, B, C, D, E, F, inside=False, defl=0.02, steps=6,
                 engine=None, open_paths=(), join=JOIN_NONE, bridge_width=4.0,
                 imprint=False, imprint_short=3.0, bridge_count=3):
    """The whole cutter as one mesh.

    Closed loops bound the cookie (even-odd: a loop inside another is a hole in
    it), and the knives stand outside the cookie — so a knife on a hole comes
    out mirrored by itself.  Open lines get a wall centred on them.  With
    `imprint`, the inner loops stop being holes and turn into such centred
    walls too, blunt and `imprint_short` lower: they press a line into the
    dough instead of cutting through it.

    `join` ties the knives together on the flange side, with bars across the
    cookie or with a plate over all of it.
    """
    profile = profile_points(A, B, C, D, E, F)
    loops = [lp for lp in (clean_loop(l) for l in loops) if lp]
    lines = [lp for lp in (clean_path(l) for l in open_paths) if lp]
    if imprint:
        if not A - imprint_short > C + EPS:
            raise CutterError("The imprint knives come out no taller than the "
                              "flange — shorten them by less.")
        loops, inner = split_inner(loops)
        for lp in inner:        # two halves: a closed wire would count as an area
            m = len(lp) // 2
            lines.extend((lp[:m + 1], lp[m:] + lp[:1]))
    if inside or C <= EPS or not loops:
        join = JOIN_NONE

    pool = MeshPool()
    half = 0.5 * F
    # a centred wall cannot end in a knife edge, it needs a top to close on
    tip = min(max(0.5 * E, 2.0 * defl), half)
    top = A - imprint_short if imprint else A
    knives = CutterBuilder(loops, inside, defl, steps, engine, pool=pool) \
        if loops else None
    walls = CutterBuilder(lines, False, defl, steps, engine, is_open=True,
                          pool=pool) if lines else None
    bridges = 0

    if join != JOIN_NONE and B > F + EPS:
        # A cookie within a hole of another (the pupil of an eye) has nothing
        # but scrap dough around it, and bridges only cross cookie.  So there
        # the flange closes over the scrap: drop the edges it would have had.
        flange = knives.contour(B)
        inside_of = [[j for j, other in enumerate(flange)
                      if j != i and point_in_loop(lp[0], other)]
                     for i, lp in enumerate(flange)]
        drop = set()
        for i, parents in enumerate(inside_of):
            if len(parents) % 2 == 1:           # the edge of a gap in the flange
                islands = [j for j, pj in enumerate(inside_of)
                           if i in pj and len(pj) == len(parents) + 1]
                if islands:
                    drop.update([i] + islands)
        knives._levels[round(B, 7)] = [lp for i, lp in enumerate(flange)
                                       if i not in drop]

    if join == JOIN_BRIDGES:
        rims = [Rim(knives, 0.0, i, False) for i in range(len(knives.contour(0.0)))]
        if walls:
            rims += [Rim(walls, half, i, True)
                     for i in range(len(walls.contour(half)))]
        bridges = add_bridges(pool, rims, bridge_width, C, bridge_count)

    if knives:
        if join == JOIN_PLATE:
            wide = max(B, F)
            knives.build([(None, 0.0), (wide, 0.0), (wide, C), (F, C), (F, C + D),
                          (E, A), (0.0, A), (0.0, C)], closed=False)
            pool.flat(knives.contour(0.0) + (walls.contour(half) if walls else []),
                      C, up=True)
        else:
            knives.build(profile)
    if walls:
        if imprint:
            shape = [(half, C), (half, top), (0.0, top)]
        else:
            shape = [(half, C), (half, C + D), (tip, A), (0.0, A)]
        if join == JOIN_PLATE:
            walls.build(shape, closed=False)
        elif join == JOIN_BRIDGES:
            # no flange of their own: the bridges carry them
            walls.build([(0.0, 0.0), (half, 0.0)] + shape[1:])
        elif imprint:
            walls.build(profile_points(top, 0.5 * B, C, 0.0, half, half))
        else:
            walls.build(profile_points(A, 0.5 * B, C, D, tip, half))

    mesh = pool.mesh()
    if mesh.Volume < 0:
        mesh.flipNormals()
    return mesh


def mesh_pieces(mesh):
    return mesh.countComponents()


def mesh_report(mesh):
    problems = []
    if not mesh.isSolid():
        problems.append("not closed")
    if mesh.hasNonManifolds():
        problems.append("non-manifold edges")
    if mesh.countNonUniformOrientedFacets():
        problems.append("inconsistent normals")
    return problems


# ── selection ─────────────────────────────────────────────────────────────────

def selected_wires():
    """Wires of whatever is selected, in global coordinates: (closed, open)"""
    import FreeCADGui
    wires = []
    for sel in FreeCADGui.Selection.getSelectionEx():
        subs = [s for s in sel.SubObjects if s.ShapeType in ("Face", "Edge", "Wire")]
        if subs:
            edges = []
            for s in subs:
                if s.ShapeType == "Edge":
                    edges.append(s)
                else:
                    wires.extend(s.Wires)
            for chain in Part.sortEdges(edges):
                wires.append(Part.Wire(chain))
            continue
        shape = getattr(sel.Object, "Shape", None)
        if shape is None or shape.isNull():
            continue
        if len(shape.Faces) > 1:
            raise CutterError(
                "\"{}\" has several faces — select the face (or its edges) "
                "to trace.".format(sel.Object.Label))
        # edges rather than Wires: a lone line or arc is a shape without a wire
        wires.extend(Part.Wire(c) for c in Part.sortEdges(shape.Edges))
    wires = [w for w in wires if w.Length > 1e-6]
    if not wires:
        raise CutterError("Select a curve first: a sketch, a Draft line or "
                          "wire, a face, or some of their edges.")
    return ([w for w in wires if w.isClosed()],
            [w for w in wires if not w.isClosed()])


def curve_plane(wires, flip=False):
    """Placement whose XY plane holds the wires, Z being the cutting direction"""
    plane = Part.Compound(wires).findPlane()
    if plane is not None:
        n, base = plane.Axis, plane.Position
    else:
        # straight lines span no plane of their own: stand the cutter as
        # upright as the line allows
        pts = [v.Point for w in wires for v in w.Vertexes]
        base = pts[0]
        u = max((p - base for p in pts), key=lambda v: v.Length)
        if u.Length < 1e-9 or any((p - base).cross(u).Length > 1e-6 * u.Length
                                  for p in pts):
            raise CutterError("The selected curves do not lie in one plane.")
        u.normalize()
        n = max((a - u * a.dot(u) for a in (V(0, 0, 1), V(0, 1, 0))),
                key=lambda v: v.Length)
        n.normalize()
    for c in (n.z, n.y, n.x):       # prefer the normal that points up
        if abs(c) > 1e-9:
            if c < 0:
                n = n.negative()
            break
    if flip:
        n = n.negative()
    return FreeCAD.Placement(base, FreeCAD.Rotation(V(0, 0, 1), n))


def wires_to_loops(wires, placement, defl):
    inv = placement.inverse()
    loops = []
    for w in wires:
        pts = [inv.multVec(p) for p in wire_points(w, 0.5 * defl)]
        if max(abs(p.z) for p in pts) > 1e-3:
            raise CutterError("The selected curves do not lie in one plane.")
        loops.append([(p.x, p.y) for p in pts])
    return loops


# ── dialog ────────────────────────────────────────────────────────────────────

def qt_modules():
    try:
        from PySide6 import QtWidgets, QtGui, QtCore
    except ImportError:
        try:
            from PySide2 import QtWidgets, QtGui, QtCore
        except ImportError:
            from PySide import QtGui, QtCore
            QtWidgets = QtGui
    return QtWidgets, QtGui, QtCore


def make_dialog(closed, opened):
    import FreeCADGui
    QtWidgets, QtGui, QtCore = qt_modules()

    class ProfileView(QtWidgets.QWidget):
        """The profile as it is dimensioned — flange on top, cutting edge down —
        with each input sitting on the dimension it sets.  A fixed schematic,
        not to scale, so the inputs stay put while the values change."""

        # outline corners, in widget pixels
        X0, XE, XF, XB = 150, 186, 216, 330     # curve side, edge, wall, flange
        Y0, YC, YD, YA = 70, 120, 290, 400      # top, flange, taper start, tip
        FIELD_W, FIELD_H = 92, 26

        def __init__(self):
            super().__init__()
            self.setFixedSize(460, 490)

        def place(self, spins):
            """Put the six inputs A..F on their dimension lines"""
            w, h = self.FIELD_W, self.FIELD_H
            spots = {
                "A": (self.X0 - 26 - w, (self.Y0 + self.YA) // 2 - h // 2),
                "B": ((self.X0 + self.XB) // 2 - w // 2, self.Y0 - 22 - h),
                "C": (self.XB + 24, (self.Y0 + self.YC) // 2 - h // 2),
                "D": (self.XF + 26, (self.YC + self.YD) // 2 - h // 2),
                "F": (self.XF + 26, self.YD - h // 2),
                "E": ((self.X0 + self.XE) // 2 - w // 2, self.YA + 26),
            }
            for key, sp in spins.items():
                sp.setParent(self)
                sp.setGeometry(spots[key][0], spots[key][1], w, h)
                sp.show()

        def paintEvent(self, _):
            p = QtGui.QPainter(self)
            p.setRenderHint(QtGui.QPainter.Antialiasing)
            p.fillRect(self.rect(), QtGui.QColor("#ffffff"))
            X0, XE, XF, XB = self.X0, self.XE, self.XF, self.XB
            Y0, YC, YD, YA = self.Y0, self.YC, self.YD, self.YA

            p.setPen(QtGui.QPen(QtGui.QColor("#202020"), 2))
            p.setBrush(QtGui.QColor("#f3d9a4"))
            p.drawPolygon(QtGui.QPolygonF([QtCore.QPointF(x, y) for x, y in (
                (X0, Y0), (XB, Y0), (XB, YC), (XF, YC), (XF, YD), (XE, YA), (X0, YA))]))

            dim = QtGui.QPen(QtGui.QColor("#606060"), 1)
            p.setPen(dim)

            def measure(x1, y1, x2, y2):
                """Dimension line with a tick at either end"""
                p.drawLine(x1, y1, x2, y2)
                if x1 == x2:
                    p.drawLine(x1 - 4, y1, x1 + 4, y1)
                    p.drawLine(x2 - 4, y2, x2 + 4, y2)
                else:
                    p.drawLine(x1, y1 - 4, x1, y1 + 4)
                    p.drawLine(x2, y2 - 4, x2, y2 + 4)

            measure(X0 - 14, Y0, X0 - 14, YA)       # A
            measure(X0, Y0 - 12, XB, Y0 - 12)       # B
            measure(XB + 12, Y0, XB + 12, YC)       # C
            measure(XF + 12, YC, XF + 12, YD)       # D
            measure(X0, YA + 12, XE, YA + 12)       # E
            # F is measured inside the wall, a leader takes it out to its input
            p.setPen(QtGui.QPen(QtGui.QColor("#606060"), 1, QtCore.Qt.DashLine))
            p.drawLine(X0, YD, XF, YD)
            p.setPen(dim)
            p.drawLine(XF, YD, XF + 26, YD)
            p.drawLine(X0 - 14, (Y0 + YA) // 2, X0 - 26, (Y0 + YA) // 2)
            p.drawLine(XB + 12, (Y0 + YC) // 2, XB + 24, (Y0 + YC) // 2)
            p.drawLine(XF + 12, (YC + YD) // 2, XF + 26, (YC + YD) // 2)
            p.drawLine((X0 + XB) // 2, Y0 - 12, (X0 + XB) // 2, Y0 - 22)
            p.drawLine((X0 + XE) // 2, YA + 12, (X0 + XE) // 2, YA + 26)

            p.setPen(QtGui.QColor("#808080"))
            p.drawText(QtCore.QRectF(0, self.height() - 22, self.width(), 18),
                       QtCore.Qt.AlignCenter,
                       "the curve runs along the left side  ·  not to scale")

    class CookieCutterDialog(QtWidgets.QDialog):

        def __init__(self):
            super().__init__(FreeCADGui.getMainWindow())
            self.closed = closed
            self.opened = opened
            self.result_name = None
            self.prefs = FreeCAD.ParamGet(PREF)
            self.setWindowTitle("Cookie Cutter  v1")
            self.setWindowFlags(QtCore.Qt.Window | QtCore.Qt.WindowStaysOnTopHint)
            self._build_ui()
            self._on_changed()

        # ── UI ────────────────────────────────────────────────────────────────

        def _spin(self, key, default, lo, hi, step=0.1, decimals=2, tip=""):
            sp = QtWidgets.QDoubleSpinBox()
            sp.setRange(lo, hi)
            sp.setDecimals(decimals)
            sp.setSingleStep(step)
            sp.setSuffix(" mm")
            sp.setValue(self.prefs.GetFloat(key, default))
            sp.setToolTip(tip)
            sp.valueChanged.connect(self._on_changed)
            return sp

        def _build_ui(self):
            root = QtWidgets.QVBoxLayout(self)
            root.setSpacing(8)

            lines = []
            if self.closed:
                lines.append(
                    "<b>{} closed curve{}</b>, {:.1f} mm around — the straight "
                    "side of the profile follows the curve.".format(
                        len(self.closed), "" if len(self.closed) == 1 else "s",
                        sum(w.Length for w in self.closed)))
            if self.opened:
                lines.append(
                    "<b>{} open line{}</b>, {:.1f} mm long — the wall is centred "
                    "on the line, the three widths are its full widths.".format(
                        len(self.opened), "" if len(self.opened) == 1 else "s",
                        sum(w.Length for w in self.opened)))
            lines.append("The flange lies in the plane of the curve, the cutting "
                         "edge rises from it.")
            root.addWidget(self._banner("<br>".join(lines)))

            row = QtWidgets.QHBoxLayout()
            root.addLayout(row)

            self.spin_A = self._spin("A", 15.0, 0.1, 500.0, 0.5,
                                     tip="A — total height of the cutter")
            self.spin_B = self._spin("B", 5.0, 0.0, 200.0, 0.5,
                                     tip="B — flange width, measured from the curve.\n"
                                         "Not wider than F = no flange.")
            self.spin_C = self._spin("C", 1.2, 0.0, 100.0,
                                     tip="C — flange thickness.  0 = no flange.")
            self.spin_D = self._spin("D", 6.0, 0.0, 500.0, 0.5,
                                     tip="D — straight part of the wall between "
                                         "the flange and the taper")
            self.spin_E = self._spin("E", 0.4, 0.0, 50.0, 0.05,
                                     tip="E — width of the cutting edge.  "
                                         "0 = knife edge.")
            self.spin_F = self._spin("F", 1.2, 0.05, 50.0,
                                     tip="F — wall width where the taper starts")
            self.view = ProfileView()
            self.view.place({"A": self.spin_A, "B": self.spin_B, "C": self.spin_C,
                             "D": self.spin_D, "E": self.spin_E, "F": self.spin_F})
            row.addWidget(self.view)

            left = QtWidgets.QVBoxLayout()
            row.addLayout(left)

            place_grp = QtWidgets.QGroupBox("Placement")
            lf = QtWidgets.QFormLayout(place_grp)
            self.combo_side = QtWidgets.QComboBox()
            self.combo_side.addItems(["Outside the curve", "Inside the curve"])
            self.combo_side.setCurrentIndex(1 if self.prefs.GetBool("Inside", False) else 0)
            self.combo_side.setEnabled(bool(self.closed))
            self.combo_side.setToolTip(
                "Outside: the cutter stands around the curve and cuts out\n"
                "exactly the drawn shape.\n"
                "Inside: the cutter stands within the curve — a stamp, or the\n"
                "wall of a hole.")
            self.check_flip = QtWidgets.QCheckBox("Flip cutting direction")
            self.check_flip.setChecked(self.prefs.GetBool("Flip", False))
            lf.addRow("Wall and flange:", self.combo_side)
            lf.addRow(self.check_flip)
            left.addWidget(place_grp)

            many_grp = QtWidgets.QGroupBox("Several curves")
            jf = QtWidgets.QFormLayout(many_grp)
            self.combo_join = QtWidgets.QComboBox()
            self.combo_join.addItems(["Not joined", "Bridges", "Full plate"])
            self.combo_join.setCurrentIndex(self.prefs.GetInt("Join", JOIN_BRIDGES))
            self.combo_join.setToolTip(
                "How the knives are held together on the flange side.\n"
                "Bridges: flat bars across the cookie, as thick as the flange.\n"
                "Full plate: the flange closes over the whole cookie.")
            self.spin_bridge = self._spin("BridgeWidth", 4.0, 0.5, 100.0, 0.5,
                                          tip="Width of the bridges")
            self.check_imprint = QtWidgets.QCheckBox("Inner curves only imprint")
            self.check_imprint.setChecked(self.prefs.GetBool("Imprint", False))
            self.check_imprint.setToolTip(
                "Off: a curve inside another cuts a hole, with the profile\n"
                "mirrored so that its straight side still faces the cookie.\n"
                "On: inner curves press a line into the dough instead — a\n"
                "blunt wall of the full width, centred on the curve, shorter.")
            self.spin_short = self._spin("ImprintShort", 3.0, 0.1, 500.0, 0.5,
                                         tip="How much lower the imprint knives "
                                             "end than the cutting ones")
            self.combo_join.currentIndexChanged.connect(self._on_changed)
            self.check_imprint.toggled.connect(self._on_changed)
            self.spin_count = QtWidgets.QSpinBox()
            self.spin_count.setRange(1, 12)
            self.spin_count.setValue(self.prefs.GetInt("BridgeCount", 3))
            self.spin_count.setToolTip(
                "Bridges holding each knife, spread round it.\n"
                "On a single one a knife swings.")
            jf.addRow("Joined by:", self.combo_join)
            jf.addRow("Bridge width:", self.spin_bridge)
            jf.addRow("Bridges per knife:", self.spin_count)
            jf.addRow(self.check_imprint)
            jf.addRow("Shorter by:", self.spin_short)
            left.addWidget(many_grp)

            mesh_grp = QtWidgets.QGroupBox("Mesh")
            mf = QtWidgets.QFormLayout(mesh_grp)
            self.spin_defl = self._spin("Deflection", 0.02, 0.002, 1.0, 0.01, 3,
                                        tip="Largest distance between the curve "
                                            "and the facets that follow it")
            self.spin_steps = QtWidgets.QSpinBox()
            self.spin_steps.setRange(1, 64)
            self.spin_steps.setValue(self.prefs.GetInt("Steps", 6))
            self.spin_steps.setToolTip(
                "Contours the taper is built from.  More of them follow the\n"
                "creases closer where the curve bends tighter than the wall\n"
                "is wide; elsewhere it makes no difference.")
            mf.addRow("Accuracy:", self.spin_defl)
            mf.addRow("Taper steps:", self.spin_steps)
            left.addWidget(mesh_grp)
            left.addStretch()

            self.status = QtWidgets.QLabel("")
            self.status.setWordWrap(True)
            root.addWidget(self.status)

            btn_row = QtWidgets.QHBoxLayout()
            self.btn_gen = QtWidgets.QPushButton("Generate")
            self.btn_gen.setDefault(True)
            self.btn_gen.clicked.connect(self._on_generate)
            btn_close = QtWidgets.QPushButton("Close")
            btn_close.clicked.connect(self.accept)
            btn_row.addStretch()
            btn_row.addWidget(self.btn_gen)
            btn_row.addWidget(btn_close)
            root.addLayout(btn_row)

        def _banner(self, html):
            lbl = QtWidgets.QLabel(html)
            lbl.setStyleSheet(
                "background:#fffbe6; border:1px solid #f0c040;"
                "border-radius:4px; padding:6px;")
            lbl.setWordWrap(True)
            return lbl

        def _say(self, text, ok=True):
            self.status.setStyleSheet("color:{};".format("#1b6e1b" if ok else "#b00020"))
            self.status.setText(text)

        # ── values ────────────────────────────────────────────────────────────

        def _dims(self):
            return tuple(sp.value() for sp in (
                self.spin_A, self.spin_B, self.spin_C,
                self.spin_D, self.spin_E, self.spin_F))

        def _on_changed(self, _=None):
            dims = self._dims()
            try:
                profile_points(*dims)
            except CutterError as e:
                self.btn_gen.setEnabled(False)
                self._say(str(e), ok=False)
                return
            self.spin_bridge.setEnabled(self.combo_join.currentIndex() == JOIN_BRIDGES)
            self.spin_count.setEnabled(self.combo_join.currentIndex() == JOIN_BRIDGES)
            self.spin_short.setEnabled(self.check_imprint.isChecked())
            self.btn_gen.setEnabled(True)
            self._say("")

        def _save(self):
            for key, v in zip("ABCDEF", self._dims()):
                self.prefs.SetFloat(key, v)
            self.prefs.SetFloat("Deflection", self.spin_defl.value())
            self.prefs.SetInt("Steps", self.spin_steps.value())
            self.prefs.SetBool("Inside", self.combo_side.currentIndex() == 1)
            self.prefs.SetBool("Flip", self.check_flip.isChecked())
            self.prefs.SetInt("Join", self.combo_join.currentIndex())
            self.prefs.SetFloat("BridgeWidth", self.spin_bridge.value())
            self.prefs.SetInt("BridgeCount", self.spin_count.value())
            self.prefs.SetBool("Imprint", self.check_imprint.isChecked())
            self.prefs.SetFloat("ImprintShort", self.spin_short.value())

        # ── generate ──────────────────────────────────────────────────────────

        def _on_generate(self):
            dims = self._dims()
            defl = self.spin_defl.value()
            inside = self.combo_side.currentIndex() == 1
            self._say("Working…")
            QtWidgets.QApplication.setOverrideCursor(QtCore.Qt.WaitCursor)
            QtWidgets.QApplication.processEvents()
            try:
                placement = curve_plane(self.closed + self.opened,
                                        self.check_flip.isChecked())
                mesh = build_cutter(
                    wires_to_loops(self.closed, placement, defl), *dims,
                    inside=inside, defl=defl, steps=self.spin_steps.value(),
                    open_paths=wires_to_loops(self.opened, placement, defl),
                    join=self.combo_join.currentIndex(),
                    bridge_width=self.spin_bridge.value(),
                    bridge_count=self.spin_count.value(),
                    imprint=self.check_imprint.isChecked(),
                    imprint_short=self.spin_short.value())
            except Exception as e:
                self._say(str(e), ok=False)
                return
            finally:
                QtWidgets.QApplication.restoreOverrideCursor()

            doc = FreeCAD.ActiveDocument
            feat = doc.getObject(self.result_name) if self.result_name else None
            if feat is None:
                feat = doc.addObject("Mesh::Feature", "CookieCutter")
                self.result_name = feat.Name
            feat.Mesh = mesh
            feat.Placement = placement
            doc.recompute()
            self._save()

            problems = mesh_report(mesh)
            pieces = mesh_pieces(mesh)
            text = "\"{}\": {} facets, {:.2f} cm³".format(
                feat.Label, mesh.CountFacets, mesh.Volume / 1000.0)
            if problems:
                self._say(text + " — check the mesh: " + ", ".join(problems), ok=False)
            elif pieces > 1:
                self._say(text + " — closed, but in {} separate pieces.".format(pieces),
                          ok=False)
            else:
                self._say(text + " — one closed solid, ready to export.")

    return CookieCutterDialog()


# ── entry point ───────────────────────────────────────────────────────────────

def run():
    QtWidgets, QtGui, QtCore = qt_modules()

    if not FreeCAD.ActiveDocument:
        QtWidgets.QMessageBox.warning(
            None, "Cookie Cutter",
            "No active document.\nOpen a document and select a closed curve first.")
        return
    try:
        closed, opened = selected_wires()
        curve_plane(closed + opened)
    except CutterError as e:
        QtWidgets.QMessageBox.warning(None, "Cookie Cutter", str(e))
        return

    dlg = make_dialog(closed, opened)
    dlg.show()

    loop = QtCore.QEventLoop()
    dlg.finished.connect(loop.quit)
    (getattr(loop, "exec", None) or loop.exec_)()


if FreeCAD.GuiUp:
    run()
