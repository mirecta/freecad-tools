# -*- coding: utf-8 -*-
"""
Cievka.FCMacro  -  parametric cable spool with a rotating connector carrier

Follows docs/cievka_doc.FCStd. Each half is a ring: the cable winds in the
outer groove, and a bore in the outer face holds a disc that turns freely and
carries the connector. The cable leaves the groove through any one of the
notches round the face, and the carrier is turned to meet it - that the carrier
turns is the point of the design, so the winding need not end anywhere in
particular.

Sizing runs connector -> diameter, cable -> height. The connector has to fit in
the carrier, the carrier sets the bore, the bore sets the drum, and only then
does the cable length decide how wide the groove has to be. Sizing the diameter
from the cable instead is what leaves the carrier too small for the plug.

    carrier radius = the connector's own corner radius + ROT_WALL
    carrier thick  = pocket depth + ROT_FLOOR, so cutting it leaves a floor
    bore radius    = carrier radius + CLR
    drum radius    = V-bead apex + WALL
    rim radius     = drum radius + GROOVE_DEPTH
    half height    = the groove width the cable needs + rim + fillet

The carrier is held by a V bead round its edge, snapping into a matching V
groove in the bore wall. The two halves snap together on flat tabs in the drum
wall: flat so they can spring, and landed on the notch grid so the two halves
of every notch line up and the cable has somewhere to come out.

Parts, none needing support:
    half A   - outer face on the bed, tabs pointing up
    half B   - outer face on the bed, slots opening up
    carrier  - x2, back on the bed, pocket facing up

All dimensions in mm.
"""

import math
import FreeCAD as App
import Part

# =================== 1. CONNECTOR - this sets the diameter ==========
CONN_L          = 35.0    # connector pocket length
CONN_W          = 11.6    # pocket width
CONN_H          = 6.0     # pocket depth
MAKE_POCKET     = True    # False = plain carriers, you cut pocket and channel
ROT_WALL        = 1.5     # carrier material outside the pocket
ROT_FLOOR       = 2.5     # and under it - this is what sets the thickness

# =================== 2. CABLE - this sets the height ================
CABLE_D         = 3.2     # measured cable diameter
CABLE_LEN       = 1500.0  # cable to store
GROOVE_DEPTH    = 6.0     # groove depth, and the fillet radius under the rim
PACK_EFF        = 0.85    # how tidily it really winds
HEIGHT_INPUT    = 0.0     # >0 = fix the height, report what it then holds

# =================== 3. BODY ========================================
WALL            = 2.5     # V-groove apex to the bottom of the cable groove
FLANGE_T        = 3.0     # rim thickness at the face
WEB_T           = 5.0     # centre web, at the parting plane
NOTCH_COUNT     = 10      # cable exits round the face
NOTCH_D         = 4.0     # how deep a notch cuts into the face

# =================== 4. CARRIER RETENTION (snap bead) ===============
ROT_T_INPUT     = 0.0     # >0 fixes the carrier thickness; 0 = pocket + floor
BEAD_H          = 1.07    # how far the bead stands proud, radially
BEAD_ANGLE      = 15.0    # its flank, from the axis

# =================== 5. HALVES JOINT (snap tabs) ====================
TAB_COUNT       = 3       # flat tabs on half A, slots on half B
TAB_W           = 9.0     # circumferential - this is what stops rotation
TAB_T           = 1.8     # radial - thin, so the tab can spring
TAB_H           = 5.0     # how far it stands above the parting plane
TAB_WALL        = 1.2     # material outside the tab, and inside the slot
BARB_H          = 0.7     # how far the barb stands proud, radially
BARB_LOCK       = 1.2     # how much of the barb is full height

# =================== 6. FITS ========================================
CLR             = 0.5     # the doc's "tolerancia" - carrier in the bore
CLR_AX          = 0.3     # axial
CLR_RAD         = 0.35    # radial, where a tab slides into a slot
CLR_TAN         = 0.15    # circumferential - this one sets how far the
                          # halves can twist, so the notches stay lined up
LEDGE_PLAY      = 0.10    # how far the joint can rattle open once snapped
MIN_BEND_N      = 4.5     # bend radius of the winding = CABLE_D * this
EXIT_OFFSET     = 0.0     # >0 swings the exit off radial, paid for in
                          # diameter; 0 is the straight radial run
EXPLODE         = 0.0
USE_DIALOG      = True
# ====================================================================

V = App.Vector


def log(m):
    App.Console.PrintMessage("[Cievka] " + m + "\n")


def warn(m):
    App.Console.PrintWarning("[Cievka] " + m + "\n")


DIALOG_FIELDS = [
    ("CONN_L",       "Connector length",            2, 300,  1, 1,   " mm"),
    ("CONN_W",       "Connector width",             2, 200,  1, 1,   " mm"),
    ("CONN_H",       "Connector depth",             1, 100,  1, 0.5, " mm"),
    ("CABLE_D",      "Cable diameter",            1.0, 20.0, 2, 0.1, " mm"),
    ("CABLE_LEN",    "Cable length",              100, 20000, 0, 50, " mm"),
    ("GROOVE_DEPTH", "Groove depth",              1.0, 60.0, 1, 0.5, " mm"),
    ("HEIGHT_INPUT", "Height (0 = from cable)",     0, 400,  1, 1,   " mm"),
    ("NOTCH_COUNT",  "Cable exits round the face",  3, 48,   0, 1,   ""),
    ("WALL",         "Wall under the groove",     1.0, 10.0, 2, 0.1, " mm"),
    ("FLANGE_T",     "Rim thickness",             1.0, 20.0, 2, 0.1, " mm"),
    ("ROT_FLOOR",    "Floor under the connector", 0.5, 20.0, 1, 0.5, " mm"),
    ("CLR",          "Carrier clearance",         0.1,  2.0, 2, 0.05," mm"),
    ("EXIT_OFFSET",  "Exit off centre",           0.0, 40.0, 1, 0.5, " mm"),
]


class Cancelled(Exception):
    pass


def ask_values():
    try:
        from PySide6 import QtWidgets
    except ImportError:
        try:
            from PySide2 import QtWidgets
        except ImportError:
            from PySide import QtGui as QtWidgets
    import FreeCADGui
    prefs = App.ParamGet("User parameter:BaseApp/Preferences/Macros/Cievka")
    g = globals()
    dlg = QtWidgets.QDialog(FreeCADGui.getMainWindow())
    dlg.setWindowTitle("Cievka parameters")
    form = QtWidgets.QFormLayout(dlg)
    pocket = QtWidgets.QCheckBox()
    pocket.setChecked(bool(prefs.GetBool("MAKE_POCKET", MAKE_POCKET)))
    form.addRow("Cut the pocket and channel", pocket)
    boxes = {}
    for key, label, lo, hi, dec, step, suf in DIALOG_FIELDS:
        sb = QtWidgets.QDoubleSpinBox()
        sb.setRange(lo, hi)
        sb.setDecimals(dec)
        sb.setSingleStep(step)
        sb.setSuffix(suf)
        sb.setValue(prefs.GetFloat(key, float(g[key])))
        form.addRow(label, sb)
        boxes[key] = sb
    bb = QtWidgets.QDialogButtonBox(
        QtWidgets.QDialogButtonBox.Ok | QtWidgets.QDialogButtonBox.Cancel)
    bb.accepted.connect(dlg.accept)
    bb.rejected.connect(dlg.reject)
    form.addRow(bb)
    if not (getattr(dlg, "exec", None) or dlg.exec_)():
        raise Cancelled("cancelled by user")
    g["MAKE_POCKET"] = pocket.isChecked()
    prefs.SetBool("MAKE_POCKET", g["MAKE_POCKET"])
    for key, sb in boxes.items():
        g[key] = sb.value()
        prefs.SetFloat(key, sb.value())


# ------------------------------------------------------------------ sizing

def carrier_thickness():
    """Thick enough that cutting the pocket leaves a floor under it.

    The carrier sits in a bore that is deeper than the carrier anyway, so
    thickness costs nothing in diameter or height - only dead space.
    """
    if ROT_T_INPUT > 0:
        return ROT_T_INPUT
    return CONN_H + ROT_FLOOR


def bead_span():
    """Half the axial length of the V bead.

    The bead is its own feature at mid thickness rather than the whole edge of
    the carrier, so that making the carrier thicker does not inflate the bead,
    and with it the bore, the drum and the whole spool.
    """
    return BEAD_H / math.tan(math.radians(BEAD_ANGLE))


def bead_zone(thickness):
    span = min(bead_span(), thickness / 2.0)
    mid = thickness / 2.0
    return mid - span, mid, mid + span


def solve_radii():
    """Connector -> carrier -> bore -> drum -> rim.

    The cable turns from circumferential to radial out in the open groove,
    riding down the fillet, not inside the slot - so the slot itself is
    straight, and a straight slot crosses the rim in the width of the rim
    instead of chewing a long chord out of it. The connector then lies along
    that same line, centred on its closest approach to the axis, which is the
    placement that needs the least carrier.

    Offsetting the line swings the exit away from dead radial, but every
    millimetre of offset is paid for in carrier radius, which is why it
    defaults to none.
    """
    d = abs(EXIT_OFFSET)
    bead_h = BEAD_H
    corner = math.hypot(CONN_L / 2.0, d + CONN_W / 2.0)
    rot_r = math.ceil((corner + ROT_WALL) * 20.0) / 20.0
    bore_r = rot_r + CLR
    drum_r = bore_r + bead_h + WALL
    flange_r = drum_r + GROOVE_DEPTH
    if d >= flange_r:
        raise RuntimeError("EXIT_OFFSET %.1f is outside the rim" % d)
    return {"rot_r": rot_r, "bore_r": bore_r, "drum_r": drum_r,
            "flange_r": flange_r, "bead_h": bead_h, "corner": corner,
            "rot_t": carrier_thickness(),
            "offset": EXIT_OFFSET, "entry_x": CONN_L / 2.0,
            "exit_angle": math.degrees(math.asin(d / flange_r))}


def run_path(geo, x_from, x_to):
    """Points along the run, outside in. x is measured along the run."""
    d = geo["offset"]
    n = max(2, int(abs(x_from - x_to) / 1.5))
    return [(x_from + (x_to - x_from) * i / float(n), d) for i in range(n + 1)]


def groove_width(geo, half_h):
    """Axial room for cable between the two fillets, both halves together."""
    return 2.0 * max(0.0, half_h - FLANGE_T - GROOVE_DEPTH)


def layer_count():
    """Turns nest into the layer below, so a layer after the first costs less."""
    if GROOVE_DEPTH < CABLE_D:
        return 0
    return 1 + int((GROOVE_DEPTH - CABLE_D) / (0.866 * CABLE_D))


def capacity(geo, half_h):
    layers = layer_count()
    per_layer = max(0, int(groove_width(geo, half_h) / CABLE_D))
    mean_d = 2.0 * geo["drum_r"] + GROOVE_DEPTH
    return layers * per_layer * PACK_EFF * math.pi * mean_d, layers, per_layer


def solve_height(geo):
    """Cable length -> how wide the groove has to be -> half height."""
    floor_h = FLANGE_T + GROOVE_DEPTH + WEB_T + CABLE_D / 2.0
    if HEIGHT_INPUT > 0:
        half_h = HEIGHT_INPUT / 2.0
    else:
        layers = max(1, layer_count())
        mean_d = 2.0 * geo["drum_r"] + GROOVE_DEPTH
        turns = CABLE_LEN / (layers * PACK_EFF * math.pi * mean_d)
        half_h = math.ceil(turns) * CABLE_D / 2.0 + FLANGE_T + GROOVE_DEPTH
    half_h = max(half_h, floor_h, carrier_thickness() + CLR_AX + WEB_T)
    return half_h


# ------------------------------------------------------------------ shapes

def revolve(profile):
    """profile = [(r, z), ...] or ("arc", mid, end); closed automatically.

    Repeated points are dropped: a bead that happens to fill the whole edge of
    a part lands its last point exactly on the corner that follows it, and a
    zero length edge is not a thing OCC will build.
    """
    profile = [q for i, q in enumerate(profile)
               if q[0] == "arc" or i == 0 or profile[i - 1][0] == "arc"
               or abs(q[0] - profile[i - 1][0]) > 1e-9
               or abs(q[1] - profile[i - 1][1]) > 1e-9]
    pts = []
    edges = []
    cur = None
    for item in profile:
        if item[0] == "arc":
            _, mid, end = item
            edges.append(Part.Arc(V(cur[0], 0, cur[1]),
                                  V(mid[0], 0, mid[1]),
                                  V(end[0], 0, end[1])).toShape())
            cur = end
        else:
            if cur is not None:
                edges.append(Part.LineSegment(V(cur[0], 0, cur[1]),
                                              V(item[0], 0, item[1])).toShape())
            cur = item
            pts.append(item)
    edges.append(Part.LineSegment(V(cur[0], 0, cur[1]),
                                  V(pts[0][0], 0, pts[0][1])).toShape())
    wire = Part.Wire(edges)
    return Part.Face(wire).revolve(V(0, 0, 0), V(0, 0, 1), 360)


def half_profile(geo, half_h):
    """Outer face at z = 0, parting plane at z = half_h.

    The bore stops at the carrier rather than running on to the web, so the one
    flat ceiling in the part is as close to the bed as it can be; the slab that
    would otherwise sit above it is hollowed from the parting plane, where the
    cavity opens upward in print and needs nothing to hold it up.
    """
    r = GROOVE_DEPTH
    ctr = (geo["flange_r"], FLANGE_T + r)
    mid = (ctr[0] + r * math.cos(math.radians(225)),
           ctr[1] + r * math.sin(math.radians(225)))
    bore_d = min(geo["rot_t"] + CLR_AX, half_h - WEB_T)
    cav_r = min(geo["bore_r"], cavity_radius(geo))
    cav_z = bore_d + WEB_T
    head = [(0.0, bore_d)]
    if cav_r > 2.0 and half_h - cav_z > 1.0:
        head += [(0.0, cav_z), (cav_r, cav_z), (cav_r, half_h)]
    else:
        head += [(0.0, half_h)]
    return head + [
        (geo["drum_r"], half_h),
        (geo["drum_r"], FLANGE_T + r),
        ("arc", mid, (geo["flange_r"], FLANGE_T)),
        (geo["flange_r"], 0.0),
        (geo["bore_r"], 0.0),
    ] + bead_steps(geo["bore_r"], geo["bead_h"], geo["rot_t"]) + [
        (geo["bore_r"], bore_d),
    ]


def bead_steps(r, h, thickness):
    """The V, as profile points, from the face inwards."""
    z0, zm, z1 = bead_zone(thickness)
    pts = []
    if z0 > 1e-9:
        pts.append((r, z0))
    pts.append((r + h, zm))
    pts.append((r, z1))
    return pts


def carrier_profile(geo):
    t = geo["rot_t"]
    return [(0.0, 0.0), (geo["rot_r"], 0.0)] + \
        bead_steps(geo["rot_r"], geo["bead_h"], t) + \
        [(geo["rot_r"], t), (0.0, t)]


def ribbon(pts, half_w, z0, z1):
    """Prism of the given width along a plan-view path."""
    left, right = [], []
    for i, (x, y) in enumerate(pts):
        j = max(0, i - 1)
        k = min(len(pts) - 1, i + 1)
        tx, ty = pts[k][0] - pts[j][0], pts[k][1] - pts[j][1]
        m = math.hypot(tx, ty) or 1.0
        nx, ny = -ty / m, tx / m
        left.append(V(x + nx * half_w, y + ny * half_w, z0))
        right.append(V(x - nx * half_w, y - ny * half_w, z0))
    loop = left + right[::-1]
    loop.append(loop[0])
    return Part.Face(Part.makePolygon(loop)).extrude(V(0, 0, z1 - z0))


def barb_lead():
    """The barb ramps back in at 45 deg, so it prints without support."""
    return BARB_H


def tab_radius(geo):
    """Tabs sit in the drum wall, measured in from the drum.

    Splitting the difference between bore and drum instead puts them in a wall
    barely thicker than the tab, leaving a tenth of a millimetre of plastic
    round each one.
    """
    return geo["drum_r"] - TAB_WALL - CLR_RAD - BARB_H - TAB_T / 2.0


def cavity_radius(geo):
    """Leave the tab room to spring inwards, and a wall inside that."""
    return tab_radius(geo) - TAB_T / 2.0 - BARB_H - CLR_RAD - TAB_WALL


def tab_angles(mirror=False):
    """Put the tabs on the notch grid.

    Whatever holds the halves together also fixes which way round they go, and
    if it lands between notches then the two halves of every notch are offset
    and the cable has nowhere to come out.
    """
    n = max(1, int(round(TAB_COUNT)))
    step = 360.0 / NOTCH_COUNT
    out = []
    for k in range(n):
        a = round(k * NOTCH_COUNT / float(n)) * step
        out.append(-a if mirror else a)
    return out


def tab_solid(geo, half_h):
    """The tab and its barb, standing on the parting plane at angle 0."""
    r0 = tab_radius(geo) - TAB_T / 2.0
    r1 = tab_radius(geo) + TAB_T / 2.0
    body = Part.makeBox(TAB_T, TAB_W, TAB_H, V(r0, -TAB_W / 2.0, half_h))
    lead = barb_lead()
    z0 = half_h + TAB_H - BARB_LOCK - lead
    prof = [V(r1, 0, z0), V(r1 + BARB_H, 0, z0),
            V(r1 + BARB_H, 0, z0 + BARB_LOCK), V(r1, 0, z0 + BARB_LOCK + lead)]
    prof.append(prof[0])
    barb = Part.Face(Part.makePolygon(prof)).extrude(V(0, TAB_W, 0))
    barb.translate(V(0, -TAB_W / 2.0, 0))
    return body.fuse(barb)


def slot_solid(geo, half_h):
    """The pocket that swallows a tab, with the ledge its barb catches on."""
    r0 = tab_radius(geo) - TAB_T / 2.0 - BARB_H - CLR_RAD
    r1 = tab_radius(geo) + TAB_T / 2.0 + CLR_RAD
    w = TAB_W + 2 * CLR_TAN
    depth = TAB_H + CLR_AX
    slot = Part.makeBox(r1 - r0, w, depth + 1.0,
                        V(r0, -w / 2.0, half_h - depth))
    ledge_z = half_h - TAB_H + BARB_LOCK + barb_lead() + LEDGE_PLAY
    relief = Part.makeBox(BARB_H, w, ledge_z - (half_h - depth),
                          V(r1, -w / 2.0, half_h - depth))
    return slot.fuse(relief)


def build_half(geo, half_h, tabs=True):
    """Half A carries the tabs, half B the slots (spec 5.2 - not identical)."""
    body = revolve(half_profile(geo, half_h))
    reach = math.sqrt(max(1.0, (geo["flange_r"] + 3.0) ** 2 - geo["offset"] ** 2))
    slot = ribbon(run_path(geo, reach, -geo["bore_r"] + 2.0),
                  (CABLE_D + CLR) / 2.0, -1.0, NOTCH_D)
    cuts = []
    for i in range(NOTCH_COUNT):
        c = slot.copy()
        c.rotate(V(0, 0, 0), V(0, 0, 1), 360.0 * i / NOTCH_COUNT)
        cuts.append(c)
    body = body.cut(Part.makeCompound(cuts))
    one = tab_solid(geo, half_h) if tabs else slot_solid(geo, half_h)
    parts = []
    for a in tab_angles(mirror=not tabs):
        c = one.copy()
        c.rotate(V(0, 0, 0), V(0, 0, 1), a)
        parts.append(c)
    pile = Part.makeCompound(parts)
    body = body.fuse(pile) if tabs else body.cut(pile)
    return body.removeSplitter()


def build_carrier(geo):
    body = revolve(carrier_profile(geo))
    if not MAKE_POCKET:
        return body.removeSplitter()
    d = geo["offset"]
    x0 = geo["entry_x"]
    hw = CONN_W / 2.0
    loop = [V(x0, d + hw, -1.0), V(x0, d - hw, -1.0),
            V(x0 - CONN_L, d - hw, -1.0), V(x0 - CONN_L, d + hw, -1.0)]
    loop.append(loop[0])
    pocket = Part.Face(Part.makePolygon(loop)).extrude(V(0, 0, CONN_H + 1.0))
    reach = math.sqrt(max(1.0, (geo["rot_r"] + 2.0) ** 2 - d ** 2))
    chan = ribbon(run_path(geo, reach, x0), (CABLE_D + CLR) / 2.0,
                  -1.0, CABLE_D + CLR)
    return body.cut(pocket.fuse(chan)).removeSplitter()


# ------------------------------------------------------------------ checks

def hanging(shape, bed_z, up):
    """Area of faces steeper than 45 deg overhang, off the bed. Rule 4."""
    total = 0.0
    worst = None
    for f in shape.Faces:
        try:
            u0, u1, v0, v1 = f.ParameterRange
            n = f.normalAt((u0 + u1) / 2.0, (v0 + v1) / 2.0)
        except Exception:
            continue
        d = n.z * up
        if d < -0.7071:
            com = f.CenterOfMass
            if abs(com.z - bed_z) > 0.05:
                total += f.Area
                if worst is None or f.Area > worst:
                    worst = f.Area
    return total, (worst or 0.0)


# ------------------------------------------------------------------ report

def echo(geo, half_h, parts):
    bend_r = MIN_BEND_N * CABLE_D
    cap, layers, per_layer = capacity(geo, half_h)
    log("=" * 62)
    log("CONNECTOR -> DIAMETER")
    log("  connector          %.1f x %.1f x %.1f mm" % (CONN_L, CONN_W, CONN_H))
    log("  its own diagonal   r %.2f  (what the carrier must contain)" % geo["corner"])
    log("  carrier            r %.2f  (D %.2f), %.2f thick"
        % (geo["rot_r"], 2 * geo["rot_r"], geo["rot_t"]))
    log("  left under it      %.2f under the pocket, %.2f under the channel"
        % (geo["rot_t"] - CONN_H, geo["rot_t"] - CABLE_D - CLR))
    log("  bore               r %.2f  (carrier + %.2f clearance)" % (geo["bore_r"], CLR))
    log("  V-bead             %.3f proud, flank %.0f deg, apex at r %.3f"
        % (geo["bead_h"], BEAD_ANGLE, geo["bore_r"] + geo["bead_h"]))
    log("  drum               r %.3f  (apex + %.2f wall)" % (geo["drum_r"], WALL))
    log("  rim                r %.3f  (D %.2f)" % (geo["flange_r"], 2 * geo["flange_r"]))
    log("")
    log("CABLE -> HEIGHT")
    log("  cable              %.1f dia, %.0f long" % (CABLE_D, CABLE_LEN))
    log("  groove             %.1f deep x %.1f wide, %d layers x %d turns"
        % (GROOVE_DEPTH, groove_width(geo, half_h), layers, per_layer))
    log("  holds              %.0f mm at %.0f%% packing   (%+.0f mm)"
        % (cap, PACK_EFF * 100, cap - CABLE_LEN))
    bore_d = min(geo["rot_t"] + CLR_AX, half_h - WEB_T)
    log("  height             %.2f  (half %.2f, bore %.2f deep, web %.2f)"
        % (2 * half_h, half_h, bore_d, WEB_T))
    log("  groove share       %.0f%% of the height"
        % (100.0 * groove_width(geo, half_h) / (2 * half_h)))
    log("")
    log("CABLE PATH")
    log("  exits              %d round the face, %.2f wide, %.1f deep"
        % (NOTCH_COUNT, CABLE_D + CLR, NOTCH_D))
    log("  run                straight, %.2f off centre, %.1f deg off radial"
        % (abs(geo["offset"]), geo["exit_angle"]))
    log("  turn out of groove on the R %.1f fillet, not in the slot" % GROOVE_DEPTH)
    log("                     wants R %.1f (%.1f x cable) - %s"
        % (bend_r, MIN_BEND_N,
           "fillet is big enough" if GROOVE_DEPTH >= bend_r else
           "raise GROOVE_DEPTH to %.1f for that" % bend_r))
    if NOTCH_D <= FLANGE_T:
        warn("notch %.1f deep does not clear the %.1f rim - the cable cannot "
             "get out" % (NOTCH_D, FLANGE_T))
    log("")
    log("PRINT (rule 4: no supports)")
    for name, shape, bed, up in parts:
        area, worst = hanging(shape, bed, up)
        log("  %-10s %s  unsupported %.0f mm2%s"
            % (name, "single solid" if len(shape.Solids) == 1 and shape.isValid()
               else "!! NOT A SINGLE VALID SOLID",
               area, "  (largest face %.0f)" % worst if worst else ""))
    log("=" * 62)


# ------------------------------------------------------------------ main

def main():
    if USE_DIALOG and App.GuiUp:
        ask_values()
    g = globals()
    g["NOTCH_COUNT"] = int(round(NOTCH_COUNT))
    g["TAB_COUNT"] = int(round(TAB_COUNT))

    geo = solve_radii()
    half_h = solve_height(geo)

    half_a = build_half(geo, half_h, tabs=True)
    half_b = build_half(geo, half_h, tabs=False)
    carrier = build_carrier(geo)

    parts = [("half A", half_a, 0.0, 1.0), ("half B", half_b, 0.0, 1.0),
             ("carrier", carrier, geo["rot_t"], -1.0)]
    echo(geo, half_h, parts)

    doc = App.ActiveDocument or App.newDocument("Cievka")
    for o in list(doc.Objects):
        if o.Name.startswith(("Cievka", "Kotuc")):
            doc.removeObject(o.Name)

    e = EXPLODE
    placed = []
    a = half_a.copy()
    placed.append(("Cievka_A", a))
    b = half_b.copy()
    b.rotate(V(0, 0, 0), V(1, 0, 0), 180)
    b.translate(V(0, 0, 2 * half_h))
    placed.append(("Cievka_B", b))
    c = carrier.copy()
    c.translate(V(0, 0, -e))
    placed.append(("Kotuc_A", c))
    d = carrier.copy()
    d.rotate(V(0, 0, 0), V(1, 0, 0), 180)
    d.translate(V(0, 0, 2 * half_h + e))
    placed.append(("Kotuc_B", d))

    for name, shp in placed:
        o = doc.addObject("Part::Feature", name)
        o.Shape = shp
    doc.recompute()
    if App.GuiUp:
        import FreeCADGui
        FreeCADGui.SendMsgToActiveView("ViewFit")
    return doc


try:
    main()
except Cancelled:
    log("cancelled")
